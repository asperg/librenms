NAG-MIB DEFINITIONS ::= BEGIN

--2.1.74
IMPORTS
    OBJECT-TYPE 		  FROM SNMPv2-SMI 
    TEXTUAL-CONVENTION,RowStatus,TimeStamp, TruthValue  FROM SNMPv2-TC   	
        MODULE-IDENTITY, OBJECT-TYPE, mib-2,
    Integer32, Counter32, Counter64,Gauge32,Unsigned32, NOTIFICATION-TYPE,
    IpAddress, TimeTicks,experimental             FROM SNMPv2-SMI
        MODULE-COMPLIANCE, OBJECT-GROUP,
    NOTIFICATION-GROUP               FROM SNMPv2-CONF
	ifIndex FROM RFC1213-MIB

    TRAP-TYPE FROM RFC-1215
    
    enterprises         FROM RFC1155-SMI;
    
    DisplayString                ::= OCTET STRING    
    MacAddress    	         ::= OCTET STRING (SIZE (17))    
    						    -- a 17 octet address
                                                    -- in the
                                                    -- "canonical"
                                                    -- order 
 
InetAddressType ::= TEXTUAL-CONVENTION
    STATUS      current
    DESCRIPTION
        "A value that represents a type of Internet address.

         unknown(0)  An unknown address type.  This value MUST
                     be used if the value of the corresponding
                     InetAddress object is a zero-length string.
                     It may also be used to indicate an IP address
                     that is not in one of the formats defined
                     below.

         ipv4(1)     An IPv4 address as defined by the
                     InetAddressIPv4 textual convention.

         ipv6(2)     An IPv6 address as defined by the
                     InetAddressIPv6 textual convention.

         ipv4z(3)    A non-global IPv4 address including a zone
                     index as defined by the InetAddressIPv4z
                     textual convention.

         ipv6z(4)    A non-global IPv6 address including a zone
                     index as defined by the InetAddressIPv6z
                     textual convention.

         dns(16)     A DNS domain name as defined by the
                     InetAddressDNS textual convention.

         Each definition of a concrete InetAddressType value must be
         accompanied by a definition of a textual convention for use
         with that InetAddressType.

         To support future extensions, the InetAddressType textual
         convention SHOULD NOT be sub-typed in object type definitions.
         It MAY be sub-typed in compliance statements in order to
         require only a subset of these address types for a compliant
         implementation.

         Implementations must ensure that InetAddressType objects
         and any dependent objects (e.g., InetAddress objects) are
         consistent.  An inconsistentValue error must be generated
         if an attempt to change an InetAddressType object would,
         for example, lead to an undefined InetAddress value.  In

         particular, InetAddressType/InetAddress pairs must be
         changed together if the address type changes (e.g., from
         ipv6(2) to ipv4(1))."
    SYNTAX       INTEGER {
                     unknown(0),
                     ipv4(1),
                     ipv6(2),
                     ipv4z(3),
                     ipv6z(4),
                     dns(16)
                 }

InetAddress ::= TEXTUAL-CONVENTION
    STATUS      current
    DESCRIPTION
        "Denotes a generic Internet address.

         An InetAddress value is always interpreted within the context
         of an InetAddressType value.  Every usage of the InetAddress
         textual convention is required to specify the InetAddressType
         object that provides the context.  It is suggested that the
         InetAddressType object be logically registered before the
         object(s) that use the InetAddress textual convention, if
         they appear in the same logical row.

         The value of an InetAddress object must always be
         consistent with the value of the associated InetAddressType
         object.  Attempts to set an InetAddress object to a value
         inconsistent with the associated InetAddressType
         must fail with an inconsistentValue error.

         When this textual convention is used as the syntax of an
         index object, there may be issues with the limit of 128
         sub-identifiers specified in SMIv2, STD 58.  In this case,
         the object definition MUST include a 'SIZE' clause to
         limit the number of potential instance sub-identifiers;
         otherwise the applicable constraints MUST be stated in
         the appropriate conceptual row DESCRIPTION clauses, or
         in the surrounding documentation if there is no single
         DESCRIPTION clause that is appropriate."
    SYNTAX       OCTET STRING (SIZE (0..255))                                                    
                                                    
    VlanList ::= TEXTUAL-CONVENTION
    STATUS      current
    DESCRIPTION
         "Vlan ID range is (1..4094), 
         Each octet within this value specifies a set of eight
         vlans, with the first octet specifying vlans 1 through
         8, the second octet specifying vlans 9 through 16, etc.
         Within each octet, the most significant bit represents
         the lowest numbered vlan, and the least significant bit
         represents the highest numbered vlan.  If that bit has 
         a value of '1' then that vlan is allowed to pass ; 
         the vlan is not allowed if its bit has a value of '0'.
         the value is a changing cells:if the maximum of vlans is 8,you
         sends one octet to me;the remnant octet's value is defaulted '0',
         the remnant octet needn't to send to me."
    SYNTAX      OCTET STRING

    PortList ::= TEXTUAL-CONVENTION
    STATUS      current
    DESCRIPTION
        "Each octet within this value specifies a set of eight
        ports, with the first octet specifying ports 1 through
        8, the second octet specifying ports 9 through 16, etc.
        Within each octet, the most significant bit represents
        the lowest numbered port, and the least significant bit
        represents the highest numbered port.  Thus, each port
        of the bridge is represented by a single bit within the
        value of this object.  If that bit has a value of '1'
        then that port is included in the set of ports; the port
        is not included if its bit has a value of '0'."
    SYNTAX      OCTET STRING
    
    EnabledStatusPrivate ::= TEXTUAL-CONVENTION
    STATUS      current
    DESCRIPTION
        "A simple status value for the object."
    SYNTAX      INTEGER { enabled(1), disabled(0) }
    
    ValidStatus ::= TEXTUAL-CONVENTION
    STATUS      current
    DESCRIPTION
        "A simple status value for the object to create and destroy
         a table entry. This is a simplified variant of RowStatus as it
         supports only two values. Setting it to valid(1) creates an entry.
         Setting it to invalid(2) destroys an entry."
    SYNTAX      INTEGER { valid(1), invalid(0) }
    
    OspfBigMetric ::= TEXTUAL-CONVENTION
    STATUS      current
    DESCRIPTION
       "The OSPF External Metric."
    SYNTAX      Integer32 (0..'FFFFFE'h)
    
    OspfAreaID ::= TEXTUAL-CONVENTION
    STATUS      current
    DESCRIPTION
       "An OSPF Area Identifier."
    SYNTAX      IpAddress
    
    SnmpAdminString ::= TEXTUAL-CONVENTION
    DISPLAY-HINT "255t"
    STATUS       current
    DESCRIPTION "An octet string containing administrative
                 information, preferably in human-readable form.

                 To facilitate internationalization, this
                 information is represented using the ISO/IEC
                 IS 10646-1 character set, encoded as an octet
                 string using the UTF-8 transformation format
                 described in [RFC2279].

                 Since additional code points are added by
                 amendments to the 10646 standard from time
                 to time, implementations must be prepared to
                 encounter any code point from 0x00000000 to
                 0x7fffffff.  Byte sequences that do not
                 correspond to the valid UTF-8 encoding of a
                 code point or are outside this range are
                 prohibited.

                 The use of control codes should be avoided.

                 When it is necessary to represent a newline,
                 the control code sequence CR LF should be used.

                 The use of leading or trailing white space should
                 be avoided.

                 For code points not directly supported by user
                 interface hardware or software, an alternative
                 means of entry and display, such as hexadecimal,
                 may be provided.

                 For information encoded in 7-bit US-ASCII,
                 the UTF-8 encoding is identical to the
                 US-ASCII encoding.

                 UTF-8 may require multiple bytes to represent a
                 single character / code point; thus the length
                 of this object in octets may be different from
                 the number of characters encoded.  Similarly,
                 size constraints refer to the number of encoded
                 octets, not the number of characters represented
                 by an encoding.

                 Note that when this TC is used for an object that
                 is used or envisioned to be used as an index, then
                 a SIZE restriction MUST be specified so that the
                 number of sub-identifiers for any object instance
                 does not exceed the limit of 128, as defined by
                 [RFC3416].

                 Note that the size of an SnmpAdminString object is
                 measured in octets, not characters.
                "
    SYNTAX       OCTET STRING (SIZE (0..255))
    
    -- InterfaceIndex contains the semantics of ifIndex and should be used
-- for any objects defined in other MIB modules that need these semantics.

InterfaceIndex ::= TEXTUAL-CONVENTION
    DISPLAY-HINT "d"
    STATUS       current
    DESCRIPTION
            "A unique value, greater than zero, for each interface or
            interface sub-layer in the managed system.  It is
            recommended that values are assigned contiguously starting
            from 1.  The value for each interface sub-layer must remain
            constant at least from one re-initialization of the entity's
            network management system to the next re-initialization."
    SYNTAX       Integer32 (1..2147483647)

InterfaceIndexOrZero ::= TEXTUAL-CONVENTION
    DISPLAY-HINT "d"
    STATUS       current
    DESCRIPTION
            "This textual convention is an extension of the
            InterfaceIndex convention.  The latter defines a greater
            than zero value used to identify an interface or interface
            sub-layer in the managed system.  This extension permits the
            additional value of zero.  the value zero is object-specific
            and must therefore be defined as part of the description of
            any object which uses this syntax.  Examples of the usage of
            zero might include situations where interface was unknown,
            or when none or all interfaces need to be referenced."
    SYNTAX       Integer32 (0..2147483647)
    
-- textual conventions

TimeFilter ::= TEXTUAL-CONVENTION
    STATUS        current
    DESCRIPTION





        "To be used for the index to a table.  Allows an application
        to download only those rows changed since a particular time.
        A row is considered changed if the value of any object in the
        row changes or if the row is created or deleted.

        When sysUpTime is equal to zero, this table shall be empty.

        One entry exists for each past value of sysUpTime, except that
        the whole table is purged should sysUpTime wrap.

        As this basic row is updated new conceptual rows are created
        (which still share the now updated object values with all
        other instances).  The number of instances which are created
        is determined by the value of sysUpTime at which the basic row
        was last updated.  One instance will exist for each value of
        sysUpTime at the last update time for the row.  A new
        timeMark instance is created for each new sysUpTime value.
        Each new conceptual row will be associated with the timeMark
        instance which was created at the value of sysUpTime with
        which the conceptual row is to be associated.

        By definition all conceptual rows were updated at or after
        time zero and so at least one conceptual row (associated with
        timeMark.0) must exist for each underlying (basic) row.

        See the appendix for further discussion of this variable.

        Consider the following fooTable:

        fooTable ...
        INDEX { fooTimeMark, fooIndex }

        FooEntry {
           fooTimeMark  TimeFilter
           fooIndex     INTEGER,
           fooCounts    Counter
        }

        Should there be two basic rows in this table (fooIndex == 1,
        fooIndex == 2) and row 1 was updated most recently at time 6,
        while row 2 was updated most recently at time 8, and both rows
        had been updated on several earlier occasions such that the
        current values were 5 and 9 respectively then the following
        fooCounts instances would exist.

        fooCounts.0.1  5
        fooCounts.0.2  9
        fooCounts.1.1  5





        fooCounts.1.2  9
        fooCounts.2.1  5
        fooCounts.2.2  9
        fooCounts.3.1  5
        fooCounts.3.2  9
        fooCounts.4.1  5
        fooCounts.4.2  9
        fooCounts.5.1  5
        fooCounts.5.2  9
        fooCounts.6.1  5
        fooCounts.6.2  9
        fooCounts.7.2  9    -- note that row 1 doesn't exist for
        fooCounts.8.2  9    -- times 7 and 8"
    SYNTAX    TimeTicks    
    
Ipv6Address ::= TEXTUAL-CONVENTION
     DISPLAY-HINT "2x:"
     STATUS       current
     DESCRIPTION
       "This data type is used to model IPv6 addresses.
        This is a binary string of 16 octets in network
        byte-order."
     SYNTAX       OCTET STRING (SIZE (16))      
--********************************************************************************************************
--******************************************************************************************************** 
                                                       
    nag                       OBJECT IDENTIFIER ::= { enterprises 40418 }
    snr                           OBJECT IDENTIFIER ::= { nag 7 }
    

    os          		      OBJECT IDENTIFIER ::= { snr 100 }
    notifications     		  OBJECT IDENTIFIER ::= { snr 101 }
    conformance          	  OBJECT IDENTIFIER ::= { snr 102 }


--xxx.100.1 
    priSystem                     OBJECT IDENTIFIER ::= { os 1 }
--xxx.100.2
    priSpanningTree               OBJECT IDENTIFIER ::= { os 2 }
--xxx.100.3
    priPorts                 	  OBJECT IDENTIFIER ::= { os 3 }
--xxx.100.4
    priIpConfig			  OBJECT IDENTIFIER ::= { os 4 } 
--xxx.100.5  
    priVlanConfig                 OBJECT IDENTIFIER ::= { os 5 }    
--xxx.100.6
    priJumblyStacking             OBJECT IDENTIFIER ::= { os 6 }
--xxx.100.7
    priUamSecurityPortMib         OBJECT IDENTIFIER ::= { os 7 }
--xxx.100.8
    priIgmpSnoopingMib            OBJECT IDENTIFIER ::= { os 8 }
--xxx.100.9
    priQinQmib         	   	  OBJECT IDENTIFIER ::= { os 9 } 
--xxx.100.10
    prisecurity			  OBJECT IDENTIFIER ::= { os 10 } 
--xxx.100.11
    priQos    			  OBJECT IDENTIFIER ::= { os 11 } 
--xxx.100.12
    primirror    		  OBJECT IDENTIFIER ::= { os 12 } 
--xxx.100.13
    pridhcp    		  	  OBJECT IDENTIFIER ::= { os 13 } 
--xxx.100.14
    priportGroup    		  OBJECT IDENTIFIER ::= { os 14 }     
--xxx.100.15    
    prisnmpMgt         	  	  OBJECT IDENTIFIER ::= { os 15 }  
--xxx.100.16
    l3               		  OBJECT IDENTIFIER ::= { os 16 }         
--xxx.100.17
    sntpMgt               	  OBJECT IDENTIFIER ::= { os 17 }
--xxx.100.18   
    urpf                          OBJECT IDENTIFIER ::= { os 18 }
--xxx.100.20   
    
    dcscm                         OBJECT IDENTIFIER ::= { os 20 }
--xxx.100.21   
    dcscm6                        OBJECT IDENTIFIER ::= { os 21 }      
--xxx.100.22      
    prClusterv2                   OBJECT IDENTIFIER ::= { os 22 }
--xxx.100.23   
    dns                           OBJECT IDENTIFIER ::= { os 23 } 
--xxx.100.25   
    ntpSnmpMIB                    OBJECT IDENTIFIER ::= { os 25 }
--xxx.100.26
    priPoeConfig    		  OBJECT IDENTIFIER ::= { os 26 }  
--xxx.100.27
    priQos2    		          OBJECT IDENTIFIER ::= { os 27 }                  
    
--xxx.100.28
    dot1xMgt    		          OBJECT IDENTIFIER ::= { os 28 } 
       
--xxx.100.29
    portMacCountLimit		          OBJECT IDENTIFIER ::= { os 29 }    
--xxx.100.30 
    ddm	          OBJECT IDENTIFIER ::= { os 30 }      
--xxx.100.31
    priPppoeIaMib		  OBJECT IDENTIFIER ::= { os 31 }  

--xxx.100.32 
    portSecurity               OBJECT IDENTIFIER ::= { os  32 }   
    
--xxx.100.33 
    macNotificationMib         OBJECT IDENTIFIER ::= { os  33 }           

--xxx.100.34
    prieeePortConfig                OBJECT IDENTIFIER ::= { os  34 }

--xxx.100.35
    portRateLimit                 OBJECT IDENTIFIER ::= { os  35 }       
    
--xxx.100.36
    macBlackholeConfig                 OBJECT IDENTIFIER ::= { os  36 }

--xxx.100.37
    priCable                 OBJECT IDENTIFIER ::= { os  37 }
	
--xxx.100.38
    priMrppRing                 OBJECT IDENTIFIER ::= { os  38 } 
	
--xxx.100.39
    erpsMgt               	  OBJECT IDENTIFIER ::= { os 39 }
	
--xxx.100.40
    fdbMacInfo               	  OBJECT IDENTIFIER ::= { os 40 }    

--xxx.100.200
    lldpPrivateInfo             OBJECT IDENTIFIER ::= { os 200 }    

-- 
ntpSnmpMIBObjects  OBJECT IDENTIFIER ::= { ntpSnmpMIB 1 }

-- MIB contains 6 groups

ntpEntInfo         OBJECT IDENTIFIER ::= { ntpSnmpMIBObjects 1 }
ntpEntStatus       OBJECT IDENTIFIER ::= { ntpSnmpMIBObjects 2 }  
            
                     
--********************************************************************************************************
--******************************************************************************************************** 

-- (xxx.100.1)   System group

--xxx.100.1.1
sysResetUnit OBJECT-TYPE
    SYNTAX  INTEGER {
                noReset(1),
                setfactory (2),
                warmReset (3)
            }
    MAX-ACCESS  read-write
    STATUS  current
    DESCRIPTION
        " setfactory(2)
	  warmReset(3)
	  noReset(1)
	  default the status is 1 "
    ::= { priSystem  1}
    
--xxx.100.1.2
sysHardwareVersion OBJECT-TYPE
    SYNTAX  DisplayString (SIZE(1..32))
    MAX-ACCESS  read-only
    STATUS  current
    DESCRIPTION
        "The version information of switch hardware "
    ::= { priSystem  2 }
    
--xxx.100.1.3
sysSoftwareVersion OBJECT-TYPE
    SYNTAX  DisplayString (SIZE(1..32))
    MAX-ACCESS  read-only
    STATUS  current
    DESCRIPTION
        "The version information of switch software "
    ::= { priSystem  3 }
    
--xxx.100.1.4
sysStackFlag OBJECT-TYPE
     SYNTAX  INTEGER {
             stack(1),
             noStack (2)
            }
    MAX-ACCESS  read-only
    STATUS  current
    DESCRIPTION
        "If it is the status of stacking"
    ::= { priSystem  4 }
    
--xxx.100.1.5
sysCPUMac OBJECT-TYPE
    SYNTAX  MacAddress
    MAX-ACCESS  read-only
    STATUS  current
    DESCRIPTION
       "The MAC Address of the switch's CPU"
    ::= { priSystem  5 }

--xxx.100.1.6
sysWriteConfig OBJECT-TYPE
    SYNTAX  INTEGER {
                write(1)
            }
    MAX-ACCESS  read-write
    STATUS  current
    DESCRIPTION
        "write(1)save the current configuration"
    ::= { priSystem  6 }  

--xxx.100.1.7
sysPowerStateTable OBJECT-TYPE 
    SYNTAX  SEQUENCE OF SysPowerStateEntry
    MAX-ACCESS  not-accessible
    STATUS  current
    DESCRIPTION
        "the power supply status is only used for chassis switch"
    ::= { priSystem   7}

--xxx.100.1.7.1
sysPowerStateEntry OBJECT-TYPE
        SYNTAX  SysPowerStateEntry
        MAX-ACCESS  not-accessible
        STATUS  current
        DESCRIPTION
            "power supply status"
        INDEX   { sysPowerSlotIndex }
        ::= { sysPowerStateTable 1 }

SysPowerStateEntry
        ::= SEQUENCE
            {
                sysPowerSlotIndex         INTEGER,
                sysPowerState		  INTEGER,
                sysPowerValue		  INTEGER,
                sysPowerType	  	  INTEGER,
                sysPowerStatus		  INTEGER
            }
            
--xxx.100.1.7.1.1
sysPowerSlotIndex OBJECT-TYPE
        SYNTAX  INTEGER 
        MAX-ACCESS  not-accessible
        STATUS  current
        DESCRIPTION
            "Module model No."
        ::= { sysPowerStateEntry 1 }
            
--xxx.100.1.7.1.2         
sysPowerState  OBJECT-TYPE
       	SYNTAX      INTEGER
        {
            sysPowerInstalled(1),
            sysPowerNotInstalled(0)
        }
        MAX-ACCESS  read-only
        STATUS      current
        DESCRIPTION "if the power supply insert"
        ::= { sysPowerStateEntry 2 }

--xxx.100.1.7.1.3
sysPowerValue OBJECT-TYPE
         SYNTAX  INTEGER
         MAX-ACCESS  read-only
         STATUS  current
         DESCRIPTION "Power Value"
            ::= { sysPowerStateEntry 3 }
                        
--xxx.100.1.7.1.4
sysPowerType OBJECT-TYPE
         SYNTAX  INTEGER
         {
            systemPower(0),
            poePower(1)
         }
         MAX-ACCESS  read-only
         STATUS  current
         DESCRIPTION "Power Type"
            ::= { sysPowerStateEntry 4 }       
            
--xxx.100.1.7.1.5
sysPowerStatus OBJECT-TYPE
         SYNTAX  INTEGER
         {
            normal(0),
            abnormal(1),
            na(2)
         }
         MAX-ACCESS  read-only
         STATUS  current
         DESCRIPTION "Power Status"
            ::= { sysPowerStateEntry 5 }  
                         
--xxx.100.1.8
sysSlotTable OBJECT-TYPE 
    SYNTAX  SEQUENCE OF SysSlotEntry
    MAX-ACCESS  not-accessible
    STATUS  current
    DESCRIPTION
        "machine information,it is only used by chassis."
    ::= { priSystem   8}

--xxx.100.1.8.1
sysSlotEntry OBJECT-TYPE
        SYNTAX  SysSlotEntry
        MAX-ACCESS  not-accessible
        STATUS  current
        DESCRIPTION
            "Switch information"
        INDEX   { sysSlotIndex }
        ::= { sysSlotTable 1 }
        
SysSlotEntry
        ::= SEQUENCE
            {
            	sysSlotIndex			INTEGER,
                sysCPUType			DisplayString,            	
                sysCPUFiveSecondIdle		INTEGER,
                sysCPUThirtySecondIdle		INTEGER,
                sysCPUFiveMinuteIdle		INTEGER,
                sysCPUIdle			INTEGER,
                sysMemorySize			INTEGER,
                sysMemoryBusy			INTEGER,
                sysFlashSize			INTEGER,
                sysTemperature			INTEGER,
                sysCpuUsage			INTEGER ,
                sysMemoryUsage			INTEGER,
                sysMemUsage                     INTEGER,
                sysPortNum                      INTEGER,
                sysFreeFlashSize                INTEGER,
                sysMemorySizeInMB               INTEGER				
            }
            
--xxx.100.1.8.1.1
sysSlotIndex OBJECT-TYPE
            SYNTAX  INTEGER 
            MAX-ACCESS  not-accessible
            STATUS  current
            DESCRIPTION
                "Module Model No."
            ::= { sysSlotEntry 1 }

--xxx.100.1.8.1.2
sysCPUType OBJECT-TYPE
    SYNTAX  DisplayString
    MAX-ACCESS  read-only
    STATUS  current
    DESCRIPTION
        "CPU type"
    ::= { sysSlotEntry  2}

--xxx.100.1.8.1.3
sysCPUFiveSecondIdle OBJECT-TYPE
    SYNTAX  INTEGER
    MAX-ACCESS  read-only
    STATUS  current
    DESCRIPTION
        "Last  5 second CPU IDLE"
    ::= { sysSlotEntry  3 }  
    
--xxx.100.1.8.1.4
sysCPUThirtySecondIdle OBJECT-TYPE
    SYNTAX  INTEGER
    MAX-ACCESS  read-only
    STATUS  current
    DESCRIPTION
        "Last 30 second CPU IDLE"
    ::= { sysSlotEntry  4 } 
    
--xxx.100.1.8.1.5
sysCPUFiveMinuteIdle OBJECT-TYPE
    SYNTAX  INTEGER
    MAX-ACCESS  read-only
    STATUS  current
    DESCRIPTION
        "Last  5 minute CPU IDLE"
    ::= { sysSlotEntry  5 } 
    
--xxx.100.1.8.1.6
sysCPUIdle OBJECT-TYPE
    SYNTAX  INTEGER
    MAX-ACCESS  read-only
    STATUS  current
    DESCRIPTION
        "From  running  CPU IDLE"
    ::= { sysSlotEntry  6 }  
    
 --xxx.100.1.8.1.7
sysMemorySize OBJECT-TYPE
    SYNTAX  INTEGER
    MAX-ACCESS  read-only
    STATUS  current
    DESCRIPTION
        "memory size"
    ::= { sysSlotEntry  7 }  
    
 --xxx.100.1.8.1.8
sysMemoryBusy OBJECT-TYPE
    SYNTAX  INTEGER
    MAX-ACCESS  read-only
    STATUS  current
    DESCRIPTION
        "memory usage rent"
    ::= { sysSlotEntry  8 } 

 --xxx.100.1.8.1.9
sysFlashSize OBJECT-TYPE
    SYNTAX  INTEGER
    MAX-ACCESS  read-only
    STATUS  current
    DESCRIPTION
        "The flash capacity of this slot."
    ::= { sysSlotEntry  9 }   

 --xxx.100.1.8.1.10
sysTemperature OBJECT-TYPE
    SYNTAX  INTEGER
    MAX-ACCESS  read-only
    STATUS  current
    DESCRIPTION
        "The Temperature of this slot.80 is 80centigrade"
    ::= { sysSlotEntry  10 }  

--xxx.100.1.8.1.11
sysCpuUsage OBJECT-TYPE
    SYNTAX  INTEGER
    MAX-ACCESS  read-only
    STATUS  current
    DESCRIPTION
        "The CPU usage of this slot."
    ::= { sysSlotEntry  11 }    
--xxx.100.1.8.1.12
sysMemoryUsage  OBJECT-TYPE
    SYNTAX  INTEGER
    MAX-ACCESS  read-only
    STATUS  current
    DESCRIPTION
        "The memory usage of this slot."
    ::= { sysSlotEntry  12 }
	
	
--xxx.100.1.8.1.21
sysMemUsage OBJECT-TYPE
    SYNTAX  INTEGER
    MAX-ACCESS  read-only
    STATUS  current
    DESCRIPTION
        "The memory usage of this slot."
    ::= { sysSlotEntry  21 }    

--xxx.100.1.8.1.22
sysPortNum OBJECT-TYPE
    SYNTAX  INTEGER
    MAX-ACCESS  read-only
    STATUS  current
    DESCRIPTION
        "The physical port number of this slot."
    ::= { sysSlotEntry  22 }

 --xxx.100.1.8.1.23
sysFreeFlashSize OBJECT-TYPE
    SYNTAX  INTEGER
    MAX-ACCESS  read-only
    STATUS  current
    DESCRIPTION
        "The free flash capacity of this slot in Kbytes."
    ::= { sysSlotEntry  23 }

 --xxx.100.1.8.1.24
sysMemorySizeInMB OBJECT-TYPE
    SYNTAX  INTEGER
    MAX-ACCESS  read-only
    STATUS  current
    DESCRIPTION
        "The memory size in MB"
    ::= { sysSlotEntry  24 }        
--********************************************************************************************************

--xxx.100.1.9
switchInfoTable OBJECT-TYPE
        SYNTAX      SEQUENCE OF SwitchInfoEntry
        MAX-ACCESS  not-accessible
        STATUS      current
        DESCRIPTION "Table of descriptive and status information about
                     switches in this system."
        ::= { priSystem 9 }
        
--xxx.100.1.9.1
switchInfoEntry OBJECT-TYPE
        SYNTAX      SwitchInfoEntry
        MAX-ACCESS  not-accessible
        STATUS      current
        DESCRIPTION "An entry in the table, containing information
                     about a single switch in this system."
        INDEX       { swSlotIndex , swUnitIndex }
        ::= { switchInfoTable 1 }

SwitchInfoEntry ::= SEQUENCE
{
    swSlotIndex             INTEGER,
    swUnitIndex             INTEGER,
    swModuleType            INTEGER
}

--xxx.100.1.9.1.1
swSlotIndex OBJECT-TYPE
        SYNTAX      INTEGER
        MAX-ACCESS  read-only
        STATUS      current
        DESCRIPTION "This object identifies the slot within the switch
                     for which this entry contains information.                    
                     While for the chassis device, the value is real switch slot number."
        ::= { switchInfoEntry 1 }
        
--xxx.100.1.9.1.2
swUnitIndex OBJECT-TYPE
        SYNTAX      INTEGER
        MAX-ACCESS  read-only
        STATUS      current
        DESCRIPTION "This object identifies the switch within the system
                     for which this entry contains information. This
                     value can never be greater than switchNumber."
        ::= { switchInfoEntry 2 }

--xxx.100.1.9.1.3
swModuleType OBJECT-TYPE
  SYNTAX      INTEGER
  {
		typeMFC(0),
		typeSFC(1),
		type1GS(2),
		type1GL(3),
		type100M1GT(4),
		type10M100MT(8),		   
		type1-M12GB(101),
		type1-12GT(102),        
		type1-210Gx(103),       
		type1-110Gx(104),       
		type1-CPU8245(105),      
		type1-BACKPLANE(106),    
		type1-24GB(107),         
		type1-24GT(108),         
		type1-36TX(109),         
		type1-4GX32TX(110),      
		type1-16FX(111),         
		type1-ES2GB(112),        
		type1-M4GX24TX(113),     
		type1-ES(114),           
		type1-MI(115),           
		type1-MII(116),          
		type1-12GB(117),         
		type1-M8GB(118),  
		type1-2XFP8GX16GB(119), 
		type1-8GX16GB(120), 
		type1-4GX24TX(121), 
		type1-L-M4GX24TX(122), 
		type1-1XFP8GX16GB(123), 
		type1-2XFP12GX12GT(124), 
		type1-12GX12GT(125), 
		type1-1XFP12GX12GT(126), 
		type1-48GT(127), 
		type1-M1XFP12GX12GT(128), 
		type1-4XFP(129), 
		type1-48GB(130), 
		type1-M44GT(131), 
		type1-M1XFP12GX12GB(132), 
		type1-12GX12GB(133), 
		type1-2XFP12GX12GB(134),
		type1-4GB12GX8GT(135),
		type1-2XFP24GB12GT(136),
		type1-24GB12GT(137),
		type1-NEWMI(138),
		type1-M1XFP12GX12GTR4(139),
		type1-12GX12GTR4(140),
		type1-2XFP12GX12GTR4(141),
		type1-E-24GB12GT(142),		
		type1-E-2XFP24GB12GT(143),
		type1-MSC(144),
		type8QSFP(145),	
		type1-FW(146),
		type1-OF(147),
		type1-MIIR2(148),
		type1-E-M16GX8GB(149),
		type1-E-4XS16GX8GB(150),
		type1-2XFP12GX12GTR5(151),
		type1-MIIR3(152),
		type1-M2XS8GX16GB(154),
		type1-28GB16GT4XS(155),
		type1-E-48GT(156),
		type1-44GB4XS(157),
		type1-20XS2Q(158),
		type2-M12GB(165),        
		type2-12GT(166),         
		type2-210Gx(167),        
		type2-110Gx(168),        
		type2-CPU8245(169),      
		type2-BACKPLANE(170),    
		type2-24GB(171),         
		type2-24GT(172),         
		type2-36TX(173),         
		type2-4GX32TX(174),      
		type2-16FX(175),         
		type2-ES2GB(176),        
		type2-M4GX24TX(177),     
		type2-ES(178),           
		type2-MI(179),           
		type2-MII(180),          
		type2-12GB(181),         
		type2-M8GB(182),        
		type2-2XFP8GX16GB(183),        
		type2-8GX16GB(184),     
		type2-4GX24TX(185),         
		type2-L-M4GX24TX(186),          
		type2-1XFP8GX16GB(187),      
		type2-2XFP12GX12GT(188),      
		type2-12GX12GT(189),          
		type2-1XFP12GX12GT(190),          
		type2-48GT(191),        
		type2-M1XFP12GX12GT(192), 
		type2-4XFP(193), 
		type2-48GB(194), 
		type2-M44GT(195), 
		type2-M1XFP12GX12GB(196), 
		type2-12GX12GB(197), 
		type2-2XFP12GX12GB(198),
		type2-4GB12GX8GT(199),
		type2-2XFP24GB12GT(200),
		type2-24GB12GT(201),
		type2-NEWMI(202),    
		type2-M1XFP12GX12GTR4(203), 
		type2-12GX12GTR4(204), 
		type2-2XFP12GX12GTR4(205), 
		type2-E-24GB12GT(206),		
		type2-E-2XFP24GB12GT(207), 	
		type2-MSC(208), 
		type2-M1XFP12GX12GTV(209),
		type2-FW(210),
		type2-OF(211),
		type2-MIIR2(212),
		type2-E-M16GX8GB(213),
		type2-E-4XS16GX8GB(214),
		type2-2XFP12GX12GTR5(215),
		type2-MIIR3(216),
		type2-M2XS8GX16GB(218),
		type2-28GB16GT4XS(219),
		type2-E-48GT(220),
		type2-44GB4XS(221),
		type2-20XS2Q(222),
		type3-M (228),
		type3-MI(229),
		type3-MII(230),		
		type3-24GT(231),
		type3-24GB(232),
		type3-ES-FW(233),		
		type3-4XFP(234),
		type3-8XFP(235),
		type3-24GT-V(236),	
		type3-24GB-V(237),
		type3-24SFP-PLUS(238),	
		type3-SUP(239),	
		type3-FAB(240),
		type3-MSC(241),
		type3-24GT-WS(242),
		type3-24GB-WS(243),
		type3-FW(244),
		type3-8QSFP(245),
		type3-OF(246),
		type3-20XS2Q(247),
		type3-FAB-TWO-CHIP(248),
		type3-08BACKPLANE(299),
		
		type4-4GT(300),
		type4-4FX(301),
		type4-2GB(302),
		type4-4TX(303),
		type4-4GB(304),
		type4-4FB(305),
		type5-M16K-SUP(320),
		type5-M16K-16Q(321),
		type5-M16K-FC(322),
		type5-M16K-48XS2Q(323),
		type5-M16K-24T24S2XS(324),
		type5-DCFW-1800-M16K(326)		
											
  } 
        MAX-ACCESS  read-only
        STATUS      current
        DESCRIPTION "Type of expansion module in this switch slot."
        ::= { switchInfoEntry 3 }   

--xxx.100.1.10
switchFileCopy                    OBJECT IDENTIFIER ::= { priSystem 10 }

--xxx.100.1.10.1
fileUserName OBJECT-TYPE
	    SYNTAX      DisplayString (SIZE(1..100))
	    MAX-ACCESS  read-write
	    STATUS      current
	    DESCRIPTION	"ftp user name"
	    ::= { switchFileCopy  1 }

--xxx.100.1.10.2
fileUserPassword OBJECT-TYPE
	    SYNTAX      DisplayString (SIZE(1..100))
	    MAX-ACCESS  read-write
	    STATUS      current
	    DESCRIPTION
	        "ftp user password"
	    ::= { switchFileCopy  2 }
	    
--xxx.100.1.10.3
fileIPaddress OBJECT-TYPE
	    SYNTAX      DisplayString (SIZE(1..100))
	    MAX-ACCESS  read-write
	    STATUS      current
	    DESCRIPTION
	        "ftp or tftp server ip address"
	    ::= { switchFileCopy  3 }

--xxx.100.1.10.4
sourceFileCopy OBJECT-TYPE
	    SYNTAX      DisplayString (SIZE(1..100))
	    MAX-ACCESS  read-write
	    STATUS      current
	    DESCRIPTION
	        "Source file name or Copy from current system configuration
	                   ."
	    ::= { switchFileCopy  4 }

--xxx.100.1.10.5
destinationFileCopy OBJECT-TYPE
	    SYNTAX      DisplayString  (SIZE(1..100))
	    MAX-ACCESS  read-write
	    STATUS      current
	    DESCRIPTION
	        "Destination file name or Copy to startup configuration."
	    ::= { switchFileCopy  5 }

--xxx.100.1.10.6
fileCopyMode OBJECT-TYPE
            SYNTAX  INTEGER
            	    {
            	    	ascii(0),
               		binary(1)
            	    }
            MAX-ACCESS  read-write
            STATUS  current
            DESCRIPTION
                "ascii(0): ASCII file mode;
                 binary(1): Binary file mode."
            ::= { switchFileCopy  6 } 
            
--xxx.100.1.10.7
fileCopyUseMode OBJECT-TYPE
            SYNTAX  INTEGER
            	    {
            	    	ftp(1),
               		tftp(2)
            	    }
            MAX-ACCESS  read-write
            STATUS  current
            DESCRIPTION
                "ftp(1): ftp server or client;
                 tftp(2): tftp server or client."
            ::= { switchFileCopy  7 } 

--xxx.100.1.10.8
fileCopy OBJECT-TYPE
            SYNTAX  INTEGER
            	    {
               		upload(1),
               		download(2)
            	    }
	    MAX-ACCESS  read-write
	    STATUS      current
	    DESCRIPTION
            "File copy configurate."
    	    ::= { switchFileCopy  8 }
    	    
--xxx.100.1.10.9
fileCopyResult OBJECT-TYPE
            SYNTAX  INTEGER
            	    {
            	        error(0),
               		ok(1),
               		uploading(2),
               		downloading(3),
               		idle(4)
            	    }
	    MAX-ACCESS  read-only
	    STATUS      current
	    DESCRIPTION
            "The result of file copy:error(0):copy file failure;ok(1):copy file success;
            uploading(2):in process of upload file;downloading(3):in process of download file;
            idle(4):be out of copy file."
    	    ::= { switchFileCopy  9 }

--xxx.100.1.10.21
fileName OBJECT-TYPE
	    SYNTAX      DisplayString (SIZE(1..100))
	    MAX-ACCESS  read-write
	    STATUS      current
	    DESCRIPTION
	        "Source file name and destination file name."
	    ::= { switchFileCopy  21 }

--xxx.100.1.10.22
fileType OBJECT-TYPE
            SYNTAX  INTEGER
            	    {
               		any(0),
               		img(1),
					cfg(2),
					log(3)
            	    }
	    MAX-ACCESS  read-write
	    STATUS      current
	    DESCRIPTION
            "File type."
    	    ::= { switchFileCopy  22 }		

--xxx.100.1.10.23
filePort OBJECT-TYPE
            SYNTAX  INTEGER
	    MAX-ACCESS  read-write
	    STATUS      current
	    DESCRIPTION
            "ftp or tftp server port number."
    	    ::= { switchFileCopy  23 }				

--xxx.100.1.10.24
fileCopyFailReason OBJECT-TYPE
            SYNTAX  DisplayString (SIZE(0..127))
	    MAX-ACCESS  read-only
	    STATUS      current
	    DESCRIPTION
            "The reason when copy file failed."
    	    ::= { switchFileCopy  24 }	

--xxx.100.1.10.25
fileCMCCCopy OBJECT-TYPE
            SYNTAX  INTEGER
            	    {
               		upload(1),
               		download(2)
            	    }
	    MAX-ACCESS  read-write
	    STATUS      current
	    DESCRIPTION
            "File copy configurate."
    	    ::= { switchFileCopy  25 }		
			
--xxx.100.1.10.26
fileCMCCIPaddress OBJECT-TYPE
	    SYNTAX      IpAddress
	    MAX-ACCESS  read-write
	    STATUS      current
	    DESCRIPTION
	        "ftp or tftp server ip address"
	    ::= { switchFileCopy  26 }

--xxx.100.1.10.27
fileCMCCCopyResult OBJECT-TYPE
            SYNTAX  INTEGER
            	    {
            	    error(0),
               		ok(1),
               		uploading(2),
               		downloading(3),
               		idle(4)
            	    }
	    MAX-ACCESS  read-only
	    STATUS      current
	    DESCRIPTION
            "The result of file copy:error(0):copy file failure;ok(1):copy file success;
            uploading(2):in process of upload file;downloading(3):in process of download file;
            idle(4):be out of copy file."
    	    ::= { switchFileCopy  27 }		
		
--xxx.100.1.11
    switchInfo            	  OBJECT IDENTIFIER ::= { priSystem 11 } 

--xxx.100.1.11.1
switchCPUType OBJECT-TYPE
    SYNTAX  DisplayString
    MAX-ACCESS  read-only
    STATUS  current
    DESCRIPTION
        "The CPU type of switch"
    ::= { switchInfo  1}

--xxx.100.1.11.2
switchCPUFiveSecondIdle OBJECT-TYPE
    SYNTAX  INTEGER
    MAX-ACCESS  read-only
    STATUS  current
    DESCRIPTION
        "Last  5 second CPU IDLE"
    ::= { switchInfo  2 }  
    
--xxx.100.1.11.3
switchCPUThirtySecondIdle OBJECT-TYPE
    SYNTAX  INTEGER
    MAX-ACCESS  read-only
    STATUS  current
    DESCRIPTION
        "Last 30 second CPU IDLE"
    ::= { switchInfo  3 } 
    
--xxx.100.1.11.4
switchCPUFiveMinuteIdle OBJECT-TYPE
    SYNTAX  INTEGER
    MAX-ACCESS  read-only
    STATUS  current
    DESCRIPTION
        "Last  5 minute CPU IDLE"
    ::= { switchInfo  4 } 
    
--xxx.100.1.11.5
switchCPUIdle OBJECT-TYPE
    SYNTAX  INTEGER
    MAX-ACCESS  read-only
    STATUS  current
    DESCRIPTION
        "From  running  CPU IDLE"
    ::= { switchInfo  5 }  
    
 --xxx.100.1.11.6
switchMemorySize OBJECT-TYPE
    SYNTAX  INTEGER
    MAX-ACCESS  read-only
    STATUS  current
    DESCRIPTION
        "memory size"
    ::= { switchInfo  6 }  
    
 --xxx.100.1.11.7
switchMemoryBusy OBJECT-TYPE
    SYNTAX  INTEGER
    MAX-ACCESS  read-only
    STATUS  current
    DESCRIPTION
        "memory usage rent"
    ::= { switchInfo  7 } 

 --xxx.100.1.11.8
switchFlashSize OBJECT-TYPE
    SYNTAX  INTEGER
    MAX-ACCESS  read-only
    STATUS  current
    DESCRIPTION
        "The flash capacity of switch."
    ::= { switchInfo  8 }   

 --xxx.100.1.11.9
switchTemperature OBJECT-TYPE
    SYNTAX  INTEGER
    MAX-ACCESS  read-only
    STATUS  current
    DESCRIPTION
        "The Temperature of switch.80 is 80centigrade"
    ::= { switchInfo  9 }  

--xxx.100.1.11.10
switchCpuUsage OBJECT-TYPE
    SYNTAX  INTEGER
    MAX-ACCESS  read-only
    STATUS  current
    DESCRIPTION
        "The CPU usage of switch."
    ::= { switchInfo  10 }  
    
--xx.100.1.11.11
switchMemoryUsage OBJECT-TYPE
	SYNTAX  INTEGER
    MAX-ACCESS  read-only
    STATUS  current
    DESCRIPTION
        "The memory usage of switch."
    ::= { switchInfo  11 } 
    
--xxx.100.1.12
sysFanTable OBJECT-TYPE 
    SYNTAX  SEQUENCE OF SysFanEntry
    MAX-ACCESS  not-accessible
    STATUS  current
    DESCRIPTION
        " the state of fan."
    ::= { priSystem   12}

--xxx.100.1.12.1
sysFanEntry OBJECT-TYPE
        SYNTAX  SysFanEntry
        MAX-ACCESS  not-accessible
        STATUS  current
        DESCRIPTION "fan supply status"
        INDEX   { sysFanIndex }
        ::= { sysFanTable 1 }
        
SysFanEntry
        ::= SEQUENCE
            {
            	sysFanIndex	      INTEGER,
                sysFanInserted        INTEGER,
                sysFanStatus	      INTEGER,
                sysFanSpeed	      INTEGER
            }
            
--xxx.100.1.12.1.1.1
sysFanIndex OBJECT-TYPE
        SYNTAX  INTEGER
        MAX-ACCESS  not-accessible
        STATUS  current
        DESCRIPTION "system fan entry index"
        ::= { sysFanEntry 1 }

--xxx.100.1.12.1.1.2
sysFanInserted  OBJECT-TYPE
    SYNTAX      INTEGER
        {
            sysFanNotInstalled(0),
            sysFanInstalled(1)            
        }
        MAX-ACCESS  read-only
        STATUS      current
        DESCRIPTION "Whether the slot fan is installed or not."
        ::= { sysFanEntry 2 } 
        
--xxx.100.1.12.1.1.3
sysFanStatus  OBJECT-TYPE
    SYNTAX      INTEGER
        {
            abnormal(1),
            normal(0)            
        }
        MAX-ACCESS  read-only
        STATUS      current
        DESCRIPTION "Whether the slot fan is normal or abnormal."
        ::= { sysFanEntry 3 } 
                
--xxx.100.1.12.1.1.4
sysFanSpeed OBJECT-TYPE
	SYNTAX  INTEGER
		{
		    none(0),
		    low(1),
		    medium-low(2),
			medium(3),
			medium-high(4),
		    high(5)
		}
    MAX-ACCESS  read-write
	STATUS	current
	DESCRIPTION
	"Status of Fan. Status: Low(1), Medium-Low(2), Medium(3), Medium-High(4), High(5), none(0) is readonly"
    ::= { sysFanEntry  4 }    

--xxx.100.1.13
switchBootImgPrimary OBJECT-TYPE
    SYNTAX      DisplayString(SIZE(1..128))
    MAX-ACCESS  read-write
    STATUS  current
    DESCRIPTION
        "Set or get filename of boot img for first time,and the length of filename is between 1 and 128."
    ::= { priSystem  13}
--xxx.100.1.14 
switchBootImgSecondary OBJECT-TYPE
    SYNTAX      DisplayString(SIZE(1..128))
    MAX-ACCESS  read-write
    STATUS  current
    DESCRIPTION
        "Set or get filename of boot img for second time,and the length of filename is between 1 and 128."
    ::= { priSystem  14}
--xxx.100.1.15 
switchBootStartUpCfg OBJECT-TYPE
  SYNTAX      DisplayString(SIZE(1..128))
  MAX-ACCESS  read-write
  STATUS  current
  DESCRIPTION
      "Set or get filename of boot startup config ,and the length of filename is between 1 and 128."
  ::= { priSystem  15}
--xxx.100.1.16    
showSwitchStartUpStatus OBJECT-TYPE
    SYNTAX  INTEGER {
                idle (1),
                success (2),
                fail(3),
                in-progress(4)
            }
    MAX-ACCESS  read-only
    STATUS  current
    DESCRIPTION
        "this object identifies start up status of switch and AM of chassis.1(idle) means hasn't wrote cfg since boot,
        2(success) means wrote cfg successfully; 3(fail) means wrote cfg fail; 
        4(in-progress) means is writing cfg right now. for chassis:it can only be used by active master"
    ::= { priSystem  16}      
    
 --xxx.100.1.17
 sysSlotBootInfoTable    OBJECT-TYPE  
 	  SYNTAX  SEQUENCE OF SysSlotBootInfoEntry
    MAX-ACCESS  not-accessible
    STATUS  current
    DESCRIPTION
        " A list of boot information.it is only used by chassis."
    ::= { priSystem   17}
            
--xxx.100.1.17.1
sysSlotBootInfoEntry    OBJECT-TYPE
        SYNTAX  SysSlotBootInfoEntry
        MAX-ACCESS  not-accessible
        STATUS  current
        DESCRIPTION
            " Entry for boot information." 
        INDEX   { sysBootInfoIndex }
        ::= { sysSlotBootInfoTable 1 } 
         
SysSlotBootInfoEntry   
        ::= SEQUENCE
            { 
                sysBootInfoIndex           INTEGER,
                sysBootImgPrimary          DisplayString,
                sysBootImgSecondary        DisplayString,
                sysBootStartupCfg          DisplayString
            } 
sysBootInfoIndex     OBJECT-TYPE
    SYNTAX      INTEGER
    MAX-ACCESS  read-only
    STATUS  current
    DESCRIPTION
        "slot NO."
    ::= { sysSlotBootInfoEntry  1}
    
sysBootImgPrimary OBJECT-TYPE
    SYNTAX      DisplayString(SIZE(1..128))
    MAX-ACCESS  read-write
    STATUS  current
    DESCRIPTION
        "Set or get filename of boot img for first time,and the length of filename is between 1 and 128."
    ::= { sysSlotBootInfoEntry  2}
--xxx.100.1.17.3 
sysBootImgSecondary OBJECT-TYPE
    SYNTAX      DisplayString(SIZE(1..128))
    MAX-ACCESS  read-write
    STATUS  current
    DESCRIPTION
        "Set or get filename of boot img for backup,and the length of filename is between 1 and 128."
    ::= { sysSlotBootInfoEntry  3}
--xxx.100.1.17.4
sysBootStartupCfg OBJECT-TYPE
  SYNTAX      DisplayString(SIZE(1..128))
  MAX-ACCESS  read-write
  STATUS  current
  DESCRIPTION
      "Set or get filename of boot startup config ,and the length of filename is between 1 and 128."
  ::= { sysSlotBootInfoEntry  4}        
             
    
--xxx.100.1.18
 sysSetBootPassword     OBJECT IDENTIFIER ::= { priSystem 18 }    

--xxx.100.1.18.1
oldPassword OBJECT-TYPE
    SYNTAX  DisplayString (SIZE(3..32))
    MAX-ACCESS  read-write
    STATUS  current
    DESCRIPTION
        "If there is a old password, you should enter the old password, then you can set the new password or delete
        the password. The length of the password is between 3 and 32, enter wrong old password or enter wrong length 
        password, you can not set new password or delete password. "
    ::= { sysSetBootPassword  1} 

--xxx.100.1.18.2
newPassword OBJECT-TYPE
    SYNTAX  DisplayString (SIZE(3..32))
    MAX-ACCESS  read-write
    STATUS  current
    DESCRIPTION
        "Enter the new password you want to set, and the length of the password is between 3 and 32."
    ::= { sysSetBootPassword  2}
    
--xxx.100.1.18.3
confirmPassword OBJECT-TYPE
    SYNTAX  DisplayString (SIZE(3..32))
    MAX-ACCESS  read-write
    STATUS  current
    DESCRIPTION
        "Enter the new password again to confirm the new password, the password entries must match."
    ::= { sysSetBootPassword  3}    

--xxx.100.1.18.4
deletePassword OBJECT-TYPE
    SYNTAX  INTEGER {
                disable (0),
                enable (1)
            }
    MAX-ACCESS  read-write
    STATUS  current
    DESCRIPTION
        "If you want to delete the password, enter '1'; if you don't want delete it, you can enter '0'
        or do nothing."
    ::= { sysSetBootPassword  4}
    
--xxx.100.1.18.5
sysSetBootPwStatus OBJECT-TYPE
    SYNTAX  INTEGER {
                disable (0),
                enable (1)
            }
    MAX-ACCESS  read-write
    STATUS  current
    DESCRIPTION
        "If you enter '1', excute the operation you set. Firstly, judge the type of deletePassword, if 
        it is '1', delete the password, and return ok; if the type is '0', then modify the password. At
        first judge the correctness of oldpassword, then judge the new password equal to confirm password.
        if they are all right, set the new password."
    ::= { sysSetBootPassword  5} 
    
    
--xxx.100.1.22 
--xxx.100.1.22
 sysAddUser     OBJECT IDENTIFIER ::= { priSystem 22 }    

--xxx.100.1.22.1
sysUserName OBJECT-TYPE
        SYNTAX      DisplayString(SIZE(1..32))
        MAX-ACCESS  read-write
        STATUS      current
        DESCRIPTION "set the username."
        ::= { sysAddUser 1 }

--xxx.100.1.22.2
sysUserPassword OBJECT-TYPE
        SYNTAX      DisplayString(SIZE(1..32))
        MAX-ACCESS  read-write
        STATUS      current
        DESCRIPTION "set the password."
        ::= { sysAddUser 2 }

--xxx.100.1.22.3
sysUserPasswordOption OBJECT-TYPE
        SYNTAX      INTEGER {
	                uncrypted(0),
	                crypted(7)
	            }
        MAX-ACCESS  read-write
        STATUS      current
        DESCRIPTION "set a uncrypted(0) or crypted(7) password,default uncrypted(0)."
        ::= { sysAddUser 3 }

--xxx.100.1.22.4
sysUserNamePrivilege OBJECT-TYPE
    SYNTAX  INTEGER (1..15)    
    MAX-ACCESS  read-write
    STATUS  current
    DESCRIPTION
        "set username privilege,default 15."
    ::= { sysAddUser  4}
    
--xxx.100.1.22.5
sysAddUserStatus OBJECT-TYPE
    SYNTAX  INTEGER {
                enable (1)
            }
    MAX-ACCESS  read-write
    STATUS  current
    DESCRIPTION
        "enable(1) user name and password."
    ::= { sysAddUser  5}  
    
--xxx.100.1.23 weiyya begin  
priPowerTable OBJECT-TYPE
        SYNTAX      SEQUENCE OF PriPowerEntry
        MAX-ACCESS  not-accessible
        STATUS      current
        DESCRIPTION "Table of power information about
                     switches in this switch."
        ::= { priSystem 23 }
        
--xxx.100.1.23.1
priPowerEntry OBJECT-TYPE
        SYNTAX      PriPowerEntry
        MAX-ACCESS  not-accessible
        STATUS      current
        DESCRIPTION "An entry in the table, containing information
                     about power in this switch."
        INDEX       { priPowerIndex}
        ::= { priPowerTable 1 }

PriPowerEntry ::= SEQUENCE
{
    priPowerIndex               INTEGER,
    priPowerPresent             INTEGER,
    priPowerSupply              INTEGER
}

--xxx.100.1.23
-- priPower     OBJECT IDENTIFIER ::= { priSystem 23 }    

--xxx.100.1.23.1.1
priPowerIndex OBJECT-TYPE
        SYNTAX      INTEGER
        MAX-ACCESS  read-only
        STATUS      current
        DESCRIPTION "get power number(power1-AC;power2-DC)."
        ::= { priPowerEntry 1 }

--xxx.100.1.23.1.2
priPowerPresent OBJECT-TYPE
        SYNTAX      INTEGER
        MAX-ACCESS  read-only
        STATUS      current
        DESCRIPTION "get power's status of present(1:present; 0: not present; 2-unknown)."
        ::= { priPowerEntry 2 }

--xxx.100.1.23.1.3
priPowerSupply OBJECT-TYPE
        SYNTAX      INTEGER 
        MAX-ACCESS  read-only
        STATUS      current
        DESCRIPTION "get power's supply status(1:up; 0:shutdown;2-unknown)."
        ::= { priPowerEntry 3 } 
        
--xxx.100.1.23.2
--priPowerStatus OBJECT-TYPE
--        SYNTAX      INTEGER
--        {
--          ac(1),
--          dc(2)
--        }
--        MAX-ACCESS  read-only
--        STATUS      current
--        DESCRIPTION "get power status(1:ac; 2:dc)."
--        ::= { priPowerTable 2 }
 
 --xxx.100.1.30
 vsfInfo     OBJECT IDENTIFIER ::= { priSystem 30 }    

--xxx.100.1.30.1
vsfCount OBJECT-TYPE
        SYNTAX      INTEGER
        MAX-ACCESS  read-only
        STATUS      current
        DESCRIPTION "vsf member count."
        ::= { vsfInfo 1 }
		
vsfModuleTable OBJECT-TYPE
        SYNTAX      SEQUENCE OF VsfModuleEntry
        MAX-ACCESS  not-accessible
        STATUS      current
        DESCRIPTION "Table of descriptive and status information about
                     vsf in this system."
        ::= { vsfInfo 2 }
        
--xxx.100.1.30.2.1
vsfModuleEntry OBJECT-TYPE
        SYNTAX      VsfModuleEntry
        MAX-ACCESS  not-accessible
        STATUS      current
        DESCRIPTION "An entry in the table, containing information
                     about  vsf in this system."
        INDEX       { vsfSlotIndex , vsfMemberIndex }
        ::= { vsfModuleTable 1 }

VsfModuleEntry ::= SEQUENCE
{
    vsfSlotIndex             INTEGER,
    vsfMemberIndex             INTEGER,
    vsfModuleType            INTEGER,
    vsfCpuMac                MacAddress,
    vsfPriority              INTEGER,
    vsfRole            	     INTEGER,
    vsfUptime                INTEGER
}

--xxx.100.1.30.2.1.1
vsfSlotIndex OBJECT-TYPE
        SYNTAX      INTEGER
        MAX-ACCESS  read-only
        STATUS      current
        DESCRIPTION "the value is real vsf slot number."
        ::= { vsfModuleEntry 1 }
        
--xxx.100.1.30.2.1.2
vsfMemberIndex OBJECT-TYPE
        SYNTAX      INTEGER
        MAX-ACCESS  read-only
        STATUS      current
        DESCRIPTION "vsf member index."
        ::= { vsfModuleEntry 2 }

--xxx.100.1.30.2.1.3
vsfModuleType OBJECT-TYPE
  SYNTAX      INTEGER
  {
		typeMFC(0),
		typeSFC(1),
		type1GS(2),
		type1GL(3),
		type100M1GT(4),
		type10M100MT(8),		   
		type1-M12GB(101),
		type1-12GT(102),        
		type1-210Gx(103),       
		type1-110Gx(104),       
		type1-CPU8245(105),      
		type1-BACKPLANE(106),    
		type1-24GB(107),         
		type1-24GT(108),         
		type1-36TX(109),         
		type1-4GX32TX(110),      
		type1-16FX(111),         
		type1-ES2GB(112),        
		type1-M4GX24TX(113),     
		type1-ES(114),           
		type1-MI(115),           
		type1-MII(116),          
		type1-12GB(117),         
		type1-M8GB(118),  
		type1-2XFP8GX16GB(119), 
		type1-8GX16GB(120), 
		type1-4GX24TX(121), 
		type1-L-M4GX24TX(122), 
		type1-1XFP8GX16GB(123), 
		type1-2XFP12GX12GT(124), 
		type1-12GX12GT(125), 
		type1-1XFP12GX12GT(126), 
		type1-48GT(127), 
		type1-M1XFP12GX12GT(128), 
		type1-4XFP(129), 
		type1-48GB(130), 
		type1-M44GT(131), 
		type1-M1XFP12GX12GB(132), 
		type1-12GX12GB(133), 
		type1-2XFP12GX12GB(134),
		type1-4GB12GX8GT(135),		
		type1-2XFP24GB12GT(136),
		type1-24GB12GT(137),
		type1-NEWMI(138),
		type1-M1XFP12GX12GTR4(139),
		type1-12GX12GTR4(140),
		type1-2XFP12GX12GTR4(141),
		type1-E-24GB12GT(142),		
		type1-E-2XFP24GB12GT(143),
		type1-MSC(144),		
		type8QSFP(145),		
		type1-FW(146),
		type1-OF(147),
		type1-MIIR2(148),
		type1-E-M16GX8GB(149),
		type1-E-4XS16GX8GB(150),
		type1-2XFP12GX12GTR5(151),
		type1-MIIR3(152),
		type1-M2XS8GX16GB(154),
		type1-28GB16GT4XS(155),
		type1-E-48GT(156),
		type1-44GB4XS(157),
		type1-20XS2Q(158),
		type2-M12GB(165),        
		type2-12GT(166),         
		type2-210Gx(167),        
		type2-110Gx(168),        
		type2-CPU8245(169),      
		type2-BACKPLANE(170),    
		type2-24GB(171),         
		type2-24GT(172),         
		type2-36TX(173),         
		type2-4GX32TX(174),      
		type2-16FX(175),         
		type2-ES2GB(176),        
		type2-M4GX24TX(177),     
		type2-ES(178),           
		type2-MI(179),           
		type2-MII(180),          
		type2-12GB(181),         
		type2-M8GB(182),        
		type2-2XFP8GX16GB(183),        
		type2-8GX16GB(184),     
		type2-4GX24TX(185),         
		type2-L-M4GX24TX(186),          
		type2-1XFP8GX16GB(187),      
		type2-2XFP12GX12GT(188),      
		type2-12GX12GT(189),          
		type2-1XFP12GX12GT(190),          
		type2-48GT(191),        
		type2-M1XFP12GX12GT(192), 
		type2-4XFP(193), 
		type2-48GB(194), 
		type2-M44GT(195), 
		type2-M1XFP12GX12GB(196), 
		type2-12GX12GB(197), 
		type2-2XFP12GX12GB(198),
		type2-4GB12GX8GT(199),		
		type2-2XFP24GB12GT(200),
		type2-24GB12GT(201),
		type2-NEWMI(202),    
		type2-M1XFP12GX12GTR4(203), 
		type2-12GX12GTR4(204), 
		type2-2XFP12GX12GTR4(205), 
		type2-E-24GB12GT(206),		
		type2-E-2XFP24GB12GT(207), 
		type2-MSC(208), 
		type2-M1XFP12GX12GTV(209),
		type2-FW(210),
		type2-OF(211),
		type2-MIIR2(212),
		type2-E-M16GX8GB(213),
		type2-E-4XS16GX8GB(214),
		type2-2XFP12GX12GTR5(215),
		type2-MIIR3(216),		
		type2-M2XS8GX16GB(218),
		type2-28GB16GT4XS(219),
		type2-E-48GT(220),
		type2-44GB4XS(221),
		type2-20XS2Q(222),
		type3-M (228),
		type3-MI(229),
		type3-MII(230),		
		type3-24GT(231),
		type3-24GB(232),
		type3-ES-FW(233),		
		type3-4XFP(234),
		type3-8XFP(235),
		type3-24GT-V(236),	
		type3-24GB-V(237),
		type3-24SFP-PLUS(238),	
		type3-SUP(239),	
		type3-FAB(240),
		type3-MSC(241),
		type3-24GT-WS(242),
		type3-24GB-WS(243),
		type3-FW(244),
		type3-8QSFP(245),
		type3-OF(246),
		type3-20XS2Q(247),
		type3-FAB-TWO-CHIP(248),
		type3-08BACKPLANE(299),		
		
		type4-4GT(300),
		type4-4FX(301),
		type4-2GB(302),
		type4-4TX(303),
		type4-4GB(304),
		type4-4FB(305),
		type5-M16K-SUP(320),
		type5-M16K-16Q(321),
		type5-M16K-FC(322),
		type5-M16K-48XS2Q(323),
		type5-M16K-24T24S2XS(324)
											
  } 
        MAX-ACCESS  read-only
        STATUS      current
        DESCRIPTION "Type of expansion module in this vsf slot."
        ::= { vsfModuleEntry 3 }    

--xxx.100.1.30.2.1.4
vsfCpuMac  OBJECT-TYPE
        SYNTAX      MacAddress
        MAX-ACCESS  read-only
        STATUS      current
        DESCRIPTION "vsf member cpu mac."
        ::= { vsfModuleEntry 4 }

--xxx.100.1.30.2.1.5
vsfPriority OBJECT-TYPE
        SYNTAX      INTEGER
        MAX-ACCESS  read-only
        STATUS      current
        DESCRIPTION "vsf member priority ."
        ::= { vsfModuleEntry 5 }


--xxx.100.1.30.2.1.6
vsfRole   OBJECT-TYPE
        SYNTAX      INTEGER
        MAX-ACCESS  read-only
        STATUS      current
        DESCRIPTION "vsf member role:1-master, 2-standby-master, 4-slave"
        ::= { vsfModuleEntry 6 }


--xxx.100.1.30.2.1.7
vsfUptime   OBJECT-TYPE
        SYNTAX      INTEGER
        MAX-ACCESS  read-only
        STATUS      current
        DESCRIPTION "vsf member running time(Seconds)."
        ::= { vsfModuleEntry 7 }

--xxx.100.1.31
sysMonitorAlarmTable OBJECT-TYPE 
    SYNTAX  SEQUENCE OF SysMonitorAlarmEntry
    MAX-ACCESS  not-accessible
    STATUS  current
    DESCRIPTION
        " the state of MonitorAlarm."
    ::= { priSystem   31}

--xxx.100.1.31.1
sysMonitorAlarmEntry OBJECT-TYPE
        SYNTAX  SysMonitorAlarmEntry
        MAX-ACCESS  not-accessible
        STATUS  current
        DESCRIPTION "MonitorAlarm supply status"
        INDEX   { sysMonitorAlarmIndex }
        ::= { sysMonitorAlarmTable 1 }
        
SysMonitorAlarmEntry
        ::= SEQUENCE
            {
            	sysMonitorAlarmIndex	      INTEGER,
                sysMonitorAlarmEnable        INTEGER,
                sysMonitorAlarmBindSet	      INTEGER,
                sysMonitorAlarmInputSet	      INTEGER,
                sysMonitorAlarmOutputSet	      INTEGER
            }
            
--xxx.100.1.31.1.1
sysMonitorAlarmIndex OBJECT-TYPE
        SYNTAX  INTEGER
        MAX-ACCESS  not-accessible
        STATUS  current
        DESCRIPTION "system MonitorAlarm entry index"
        ::= { sysMonitorAlarmEntry 1 }

--xxx.100.1.31.1.2
sysMonitorAlarmEnable  OBJECT-TYPE
    SYNTAX      INTEGER
        {
            sysMonitorAlarmNotEnable(0),
            sysMonitorAlarmEnable(1)            
        }
        MAX-ACCESS  read-only
        STATUS      current
        DESCRIPTION "Whether the slot MonitorAlarm is enabled or not."
        ::= { sysMonitorAlarmEntry 2 } 
        
--xxx.100.1.31.1.3
sysMonitorAlarmBindSet  OBJECT-TYPE
    SYNTAX      INTEGER
        {
            input1-output1(1),  
            input1-output2(2), 
            input2-output1(3),
            input2-output2(4)                   
        }
        MAX-ACCESS  read-only
        STATUS      current
        DESCRIPTION "Whether the slot fan is normal or abnormal."
        ::= { sysMonitorAlarmEntry 3 } 
                
--xxx.100.1.31.1.4
sysMonitorAlarmInputSet OBJECT-TYPE
	SYNTAX  INTEGER
		{
		  	input1-high(1),
		    input1-low(2),
			input2-high(3),
			input2-low(4)	   
		}
    MAX-ACCESS  read-write
	STATUS	current
	DESCRIPTION
	"InputSet of MonitorAlarm. Status: input1-high(1), input1-low(2), input2-high(3), input2-low(4) is readonly"
    ::= { sysMonitorAlarmEntry  4 }    
    
--xxx.100.1.31.1.5    
sysMonitorAlarmOutputSet OBJECT-TYPE
	SYNTAX  INTEGER
		{
		    output1-high(1),
		    output1-low(2),
			output2-high(3),
			output2-low(4)
		}
    MAX-ACCESS  read-write
	STATUS	current
	DESCRIPTION
	"Output of MonitorAlarm. Status: output1-high(1), output1-low(2), output2-high(3)), output2-low(4)is readonly"
    ::= { sysMonitorAlarmEntry  5 } 

--xxx.100.1.100 
deviceTypeID OBJECT-TYPE
  SYNTAX      INTEGER
  MAX-ACCESS  read-only
  STATUS      current
  DESCRIPTION
      "the hardware type ID of the physical entity."
  ::= { priSystem  100}  
  
--xxx.100.1.101
rpsPowerVoltage OBJECT-TYPE
  SYNTAX      INTEGER
  MAX-ACCESS  read-only
  STATUS      current
  DESCRIPTION
      "show rps power voltage."
  ::= { priSystem  101}   
--********************************************************************************************************
--********************************************************************************************************  
        
-- (xxx.100.2)   Spanning tree group

--xxx.100.2.1 
spanGlobalEnable OBJECT-TYPE
    SYNTAX  INTEGER {
                enable (1),
                disable (2)
            }
    MAX-ACCESS  read-write
    STATUS  current
    DESCRIPTION
        " Enable or disable the Spanning Tree algorithm in the switch."
    ::= { priSpanningTree  1 }
    
--******************************************************************************************************** 
--xxx.100.2.2
    mstpMgt               	  	  OBJECT IDENTIFIER ::= { priSpanningTree 2 }
--xxx.100.2.2.1
    mstpSystemGroup               	  OBJECT IDENTIFIER ::= { mstpMgt 1 }  
--xxx.100.2.2.1.1
        mstpEnable OBJECT-TYPE
            SYNTAX  INTEGER  
            	   {
			enable(1),
			disable(0)
                    }         	
            MAX-ACCESS  read-create
            STATUS  current
            DESCRIPTION
                "Enable or disable the Spanning Tree algorithm in the switch. 
                 This scalar takes effect when Spanning Tree is globally enabled."
            ::= { mstpSystemGroup  1 }

--xxx.100.2.2.1.2
        mstpTCFlush OBJECT-TYPE
            SYNTAX  INTEGER
            	   {
			enable(1),
			disable(2),
			protect(3)
                    }             
            MAX-ACCESS  read-create
            STATUS  current
            DESCRIPTION
                "configure global style of TC FLUSH"
             ::= { mstpSystemGroup  2 }     
--xxx.100.2.2.1.3
        mstpForwardTime OBJECT-TYPE
            SYNTAX  INTEGER           	
            MAX-ACCESS  read-only
            STATUS  current
            DESCRIPTION
                "This time value, measured in units of hundredths of a second, 
                controls how fast a port changes its spanning state when moving 
                towards the Forwarding state.  The value determines how long the 
                port stays in each of the Listening and Learning states, which 
                precede the Forwarding state.  This value is also used, when a 
                topology change has been detected and is underway, to age all 
                dynamic entries in the Forwarding Database."
            ::= { mstpSystemGroup  3 }

--xxx.100.2.2.1.4
        mstpHelloTime OBJECT-TYPE
            SYNTAX  INTEGER    
            MAX-ACCESS  read-only
            STATUS  current
            DESCRIPTION
                "The amount of time between the transmission of Configuration 
                bridge PDUs by this node on any port when it is the root of 
                the spanning tree or trying to become so, in units of hundredths 
                of a second. This is the actual value that this bridge is currently using."
            ::= { mstpSystemGroup  4 }
              
--xxx.100.2.2.1.5
        mstpMaxage OBJECT-TYPE
            SYNTAX  INTEGER          	
            MAX-ACCESS  read-only
            STATUS  current
            DESCRIPTION
                "The maximum age of Spanning Tree Protocol information learned 
                from the network on any port before it is discarded, in units 
                of hundredths of a second.  This is the actual value that this 
                bridge is currently using."
            ::= { mstpSystemGroup  5 }

--xxx.100.2.2.1.6
        mstpMaxhop OBJECT-TYPE
            SYNTAX  INTEGER (1..40)
            MAX-ACCESS  read-create
            STATUS  current
            DESCRIPTION
                "setting global Maxhop of mstp"
            ::= { mstpSystemGroup  6 }  
--xxx.100.2.2.1.7
        mstpMode OBJECT-TYPE
            SYNTAX  INTEGER         
            	   {
			stp(0),
			rstp(2),			
			mstp(3)
                    }                 	
            MAX-ACCESS  read-create
            STATUS  current
            DESCRIPTION
               "setting global mode of mstp,stp or rstp"
            ::= { mstpSystemGroup  7 }

--xxx.100.2.2.1.8
        mstpName OBJECT-TYPE
            SYNTAX  DisplayString (SIZE(1..32))
            MAX-ACCESS  read-create
            STATUS  current
            DESCRIPTION
                "setting the name of mst"
            ::= { mstpSystemGroup  8 }  
--xxx.100.2.2.1.9
        mstpRevisionLevel OBJECT-TYPE
            SYNTAX  INTEGER  (0..65535)          	
            MAX-ACCESS  read-create
            STATUS  current
            DESCRIPTION
                "setting the global revision level of mstp"
            ::= { mstpSystemGroup  9 }

--xxx.100.2.2.1.10
        mstpBridgeForwardDelay OBJECT-TYPE
            SYNTAX  INTEGER (4..30)           	
            MAX-ACCESS  read-create
            STATUS  current
            DESCRIPTION
                "setting global Forwardtime of mstp"
            ::= { mstpSystemGroup  10 }
            
--xxx.100.2.2.1.11
        mstpBridgeHelloTime OBJECT-TYPE
            SYNTAX  INTEGER (1..10)    
            MAX-ACCESS  read-create
            STATUS  current
            DESCRIPTION
                "setting global HelloTime of mstp"
            ::= { mstpSystemGroup  11 }
         
--xxx.100.2.2.1.12
        mstpBridgeMaxage OBJECT-TYPE
            SYNTAX  INTEGER   (6..40)         	
            MAX-ACCESS  read-create
            STATUS  current
            DESCRIPTION
                "setting global Maxage of mstp"
            ::= { mstpSystemGroup  12 } 

--xxx.100.2.2.3
mstpInstancePortTable OBJECT-TYPE 
    SYNTAX  SEQUENCE OF MstpInstancePortEntry
    MAX-ACCESS  not-accessible
    STATUS  current
    DESCRIPTION
        " interrelated parameter list of instance and port "
    ::= { mstpMgt   3}
            
--xxx.100.2.2.3.1
mstpInstancePortEntry OBJECT-TYPE
        SYNTAX  MstpInstancePortEntry
        MAX-ACCESS  not-accessible
        STATUS  current
        DESCRIPTION
            " The index of this table is instance ID and port index" 
        INDEX   { mstpInstancePortInstanceID,mstpInstancePortPortIndex }
        ::= { mstpInstancePortTable 1 }

MstpInstancePortEntry
        ::= SEQUENCE
            {
                mstpInstancePortInstanceID               		INTEGER,
                mstpInstancePortPortIndex				INTEGER,
                mstpInstancePortCost					INTEGER,
                mstpInstancePortPriority				INTEGER,
                mstpInstancePortRootGuard				INTEGER,
                mstpInstancePortID                                      OCTET STRING,
                mstpInstancePortExtRootPathCost                         Unsigned32,
                mstpInstancePortIntRootPathCost                         Unsigned32,  
                mstpInstancePortState                                   INTEGER,  
                mstpInstancePortRole                                    INTEGER, 
                mstpInstancePortDesignatedBridgeID                      OCTET STRING,  
                mstpInstancePortDesignatedPortID                        OCTET STRING 
            }
            
--xxx.100.2.2.3.1.1
mstpInstancePortInstanceID  OBJECT-TYPE
            SYNTAX  INTEGER 
            MAX-ACCESS  not-accessible
            STATUS  current
            DESCRIPTION
                " instance ID"
            ::= { mstpInstancePortEntry 1 }
            
--xxx.100.2.2.3.1.2         
mstpInstancePortPortIndex  OBJECT-TYPE
	SYNTAX      INTEGER
        MAX-ACCESS  not-accessible
        STATUS      current
        DESCRIPTION "port index"
        ::= { mstpInstancePortEntry 2 }
--xxx.100.2.2.3.1.3         
mstpInstancePortCost  OBJECT-TYPE 
        SYNTAX      INTEGER (1..200000000)
        MAX-ACCESS  read-create
        STATUS      current
        DESCRIPTION "port cost of port under the special instance"
        ::= { mstpInstancePortEntry 3 }  
--xxx.100.2.2.3.1.4         
mstpInstancePortPriority  OBJECT-TYPE
        SYNTAX      INTEGER (0..240)
        MAX-ACCESS  read-create
        STATUS      current
        DESCRIPTION "port priority of port under the special instance"
        ::= { mstpInstancePortEntry 4 } 
         
--xxx.100.2.2.3.1.5        
mstpInstancePortRootGuard  OBJECT-TYPE
        SYNTAX      INTEGER
            	   {
			enable(1),
			disable(0)
                    }          
        MAX-ACCESS  read-create
        STATUS      current
        DESCRIPTION "rootguard enable/disable on the current instance"
        ::= { mstpInstancePortEntry 5 }
        
--xxx.100.2.2.3.1.6         
mstpInstancePortID  OBJECT-TYPE
        SYNTAX      OCTET STRING          	
        MAX-ACCESS  read-only
        STATUS      current
        DESCRIPTION "ID of port which receive a BPDU"  
        ::= { mstpInstancePortEntry 6 } 
        
--xxx.100.2.2.3.1.7         
mstpInstancePortExtRootPathCost  OBJECT-TYPE
        SYNTAX      Unsigned32          	
        MAX-ACCESS  read-only
        STATUS      current
        DESCRIPTION "the path cost from self bridge to Root bridge"  
        ::= { mstpInstancePortEntry 7 }  

--xxx.100.2.2.3.1.8         
mstpInstancePortIntRootPathCost  OBJECT-TYPE
        SYNTAX      Unsigned32          	
        MAX-ACCESS  read-only
        STATUS      current
        DESCRIPTION "the path cost from self bridge to Region Root"  
        ::= { mstpInstancePortEntry 8 } 

--xxx.100.2.2.3.1.9         
mstpInstancePortState  OBJECT-TYPE
        SYNTAX      INTEGER
              	    {
			block(0),
			forwarding(1),
			learning(2)
                    }                	
        MAX-ACCESS  read-only
        STATUS      current
        DESCRIPTION "the port state in the instance"  
        ::= { mstpInstancePortEntry 9 } 
 
--xxx.100.2.2.3.1.10         
mstpInstancePortRole  OBJECT-TYPE
        SYNTAX      INTEGER
              	    {            	    
			nonstp(0),
			alternate(1),
			root(2),
			designated(3),
			backup(4),
			master(5),
			disabled(6)									
                    }                	
        MAX-ACCESS  read-only
        STATUS      current
        DESCRIPTION "the port role in the instance"  
        ::= { mstpInstancePortEntry 10 }  
        
--xxx.100.2.2.3.1.11         
mstpInstancePortDesignatedBridgeID  OBJECT-TYPE
        SYNTAX      OCTET STRING                	
        MAX-ACCESS  read-only
        STATUS      current
        DESCRIPTION "the designated bridge ID"  
        ::= { mstpInstancePortEntry 11 } 
        
--xxx.100.2.2.3.1.12         
mstpInstancePortDesignatedPortID  OBJECT-TYPE
        SYNTAX      OCTET STRING                	
        MAX-ACCESS  read-only
        STATUS      current
        DESCRIPTION "the designated port ID"  
        ::= { mstpInstancePortEntry 12 }                                                               
--******************************************************************************************************** 

--xxx.100.2.2.2
mstpInstanceTable OBJECT-TYPE 
    SYNTAX  SEQUENCE OF MstpInstanceEntry
    MAX-ACCESS  not-accessible
    STATUS  current
    DESCRIPTION
        " correlative information list with instance"
    ::= { mstpMgt   2}
            
--xxx.100.2.2.2.1
mstpInstanceEntry OBJECT-TYPE
        SYNTAX  MstpInstanceEntry
        MAX-ACCESS  not-accessible
        STATUS  current
        DESCRIPTION
            " The index of this table is instance ID"
        INDEX   { mstpInstanceID}
        ::= { mstpInstanceTable 1 }

MstpInstanceEntry
        ::= SEQUENCE
            {
                mstpInstanceID               			INTEGER,
                mstpInstanceVlans				DisplayString,
                mstpInstanceSwitchPriority			INTEGER,
                mstpInstanceRegionRootID                        OCTET STRING,
                mstpInstanceIntRootPathCost                     Unsigned32,   
                mstpInstanceRootPortID                          OCTET STRING                
            }
            
--xxx.100.2.2.2.1.1
mstpInstanceID  OBJECT-TYPE
            SYNTAX  INTEGER 
            MAX-ACCESS  not-accessible
            STATUS  current
            DESCRIPTION
                " instance ID"
            ::= { mstpInstanceEntry 1 }
            
--xxx.100.2.2.2.1.2         
mstpInstanceVlans  OBJECT-TYPE
	SYNTAX      DisplayString (SIZE(0..512))
        MAX-ACCESS  read-create
        STATUS      current
        DESCRIPTION " the map of vlans to instance.The input format is  consonant with cli."
        ::= { mstpInstanceEntry 2 }
        
--xxx.100.2.2.2.1.3         
mstpInstanceSwitchPriority  OBJECT-TYPE 
        SYNTAX      INTEGER (0..61440)
        MAX-ACCESS  read-create
        STATUS      current
        DESCRIPTION " the priority of the router in the special instance."
        ::= { mstpInstanceEntry 3 }
          
--xxx.100.2.2.2.1.4         
mstpInstanceRegionRootID  OBJECT-TYPE 
        SYNTAX      OCTET STRING
        MAX-ACCESS  read-only
        STATUS      current
        DESCRIPTION " the region root ID in the special instance."
        ::= { mstpInstanceEntry 4 }
          
--xxx.100.2.2.2.1.5         
mstpInstanceIntRootPathCost  OBJECT-TYPE 
        SYNTAX      Unsigned32
        MAX-ACCESS  read-only
        STATUS      current
        DESCRIPTION " the path cost from self bridge to Region Root."
        ::= { mstpInstanceEntry 5 }
        
--xxx.100.2.2.2.1.6         
mstpInstanceRootPortID  OBJECT-TYPE 
        SYNTAX      OCTET STRING
        MAX-ACCESS  read-only
        STATUS      current
        DESCRIPTION " the root port ID in the special instance."
        ::= { mstpInstanceEntry 6 }                                                               
--********************************************************************************************************                                                   
--xxx.100.2.2.4
mstpPortInfoTable OBJECT-TYPE 
    SYNTAX  SEQUENCE OF MstpPortInfoEntry
    MAX-ACCESS  not-accessible
    STATUS  current
    DESCRIPTION
        " mstp information list of port"
    ::= { mstpMgt   4}
            
--xxx.100.2.2.4.1
mstpPortInfoEntry OBJECT-TYPE
        SYNTAX  MstpPortInfoEntry
        MAX-ACCESS  not-accessible
        STATUS  current
        DESCRIPTION
            " The index of this table is port index"
        INDEX   { mstpPortInfoPortIndex}
        ::= { mstpPortInfoTable 1 }

MstpPortInfoEntry
        ::= SEQUENCE
            {
                mstpPortInfoPortIndex               		INTEGER,
                mstpPortInfoEnable				INTEGER,
                mstpPortLinkType				INTEGER,
                mstpPortMcheck					INTEGER,
                mstpPortPortFast				INTEGER,
                mstpPortFormat					INTEGER,
                mstpPortDigestSnp				INTEGER,
                mstpPortTCFlush					INTEGER                                                                               
            }
            
--xxx.100.2.2.4.1.1
mstpPortInfoPortIndex  OBJECT-TYPE
            SYNTAX  INTEGER 
            MAX-ACCESS  not-accessible
            STATUS  current
            DESCRIPTION
                " port index"
            ::= { mstpPortInfoEntry 1 }

--xxx.100.2.2.4.1.2         
mstpPortInfoEnable  OBJECT-TYPE
	SYNTAX      INTEGER
			{
				disable(0),
				enable(1)
			}
        MAX-ACCESS  read-create
        STATUS      current
        DESCRIPTION "enable/disable mstp on the port."
        ::= { mstpPortInfoEntry 2 }
                    
--xxx.100.2.2.4.1.3         
mstpPortLinkType  OBJECT-TYPE
	SYNTAX      INTEGER
			{
				auto(2),
				force-true(1),
				force-false(0)
			}
        MAX-ACCESS  read-create
        STATUS      current
        DESCRIPTION " the p2p link type of the port"
        ::= { mstpPortInfoEntry 3 }
        
--xxx.100.2.2.4.1.4         
mstpPortMcheck  OBJECT-TYPE 
        SYNTAX      INTEGER 
        		{
        			untrigger(0),
        			trigger(1)
        		}
        MAX-ACCESS  read-create
        STATUS      current
        DESCRIPTION "trigger/untrigger"
        ::= { mstpPortInfoEntry 4 }
          
--xxx.100.2.2.4.1.5         
mstpPortPortFast  OBJECT-TYPE
        SYNTAX      INTEGER 
        		{
        			default(0),
        			bpdufilter(1),
        			bpduguard(2),
        			noportfast(3)-- no spanningtree portfast		
        		}
        MAX-ACCESS  read-create
        STATUS      current
                DESCRIPTION "
                default:the port mode is portfast mode
                bpdufilter:the port mode is portfast mode with bpdufilter
                bpduguard:the port mode is portfast mode with bpduguard
                noportfast:the port mode is not portfast mode"
        ::= { mstpPortInfoEntry 5 } 
         
--xxx.100.2.2.4.1.6        
mstpPortFormat  OBJECT-TYPE
        SYNTAX      INTEGER
            	   {
			standard(0),
			privacy(1),
			auto(2)
                    }          
        MAX-ACCESS  read-create
        STATUS      current
        DESCRIPTION "which mode can be setted up port of message format function"
        ::= { mstpPortInfoEntry 6 }  
                  
--xxx.100.2.2.4.1.7         
mstpPortDigestSnp  OBJECT-TYPE 
        SYNTAX      INTEGER 
            	   {
			enable(1),
			disable(0)
                    }           		
        MAX-ACCESS  read-create
        STATUS      current
        DESCRIPTION "Whether the port use peer's authentication key"
        ::= { mstpPortInfoEntry 7 }  
        
--xxx.100.2.2.4.1.8         
mstpPortTCFlush  OBJECT-TYPE
        SYNTAX      INTEGER 
            	   {
			enable(1),
			disable(2),
			protect(3),
			useglobal(0)
                    }         	
        MAX-ACCESS  read-create
        STATUS      current
        DESCRIPTION "when topology is changed,  how to flush the mac"  
        ::= { mstpPortInfoEntry 8 }                                                               
--********************************************************************************************************
--******************************************************************************************************** 
    
-- (xxx.100.3)   Ports group

--xxx.100.3.1
portCount OBJECT-TYPE
    SYNTAX  INTEGER (1..256)
    MAX-ACCESS  read-only
    STATUS  current
    DESCRIPTION
        " The total number of ports in the system."
    ::= { priPorts  1 }

--xxx.100.3.2
priPortTable OBJECT-TYPE
    SYNTAX  SEQUENCE OF PriPortEntry
    MAX-ACCESS  not-accessible
    STATUS  current
    DESCRIPTION
        " A list of port entries."
    ::= { priPorts   2 }

--xxx.100.3.2.1
    priPortEntry OBJECT-TYPE
        SYNTAX  PriPortEntry
        MAX-ACCESS  not-accessible
        STATUS  current
        DESCRIPTION
            " A port entry containing port information, 
            status, and control."
        INDEX   { portIndex }
        ::= { priPortTable 1 }

    PriPortEntry
        ::= SEQUENCE
            {
                portIndex               INTEGER,
                portName                DisplayString,
                switchNum		INTEGER,
                slotNum 		INTEGER,
                portType                INTEGER,
                flowControlStatus	INTEGER,
                bandwidthControlStatus	INTEGER,  
                maxBandwidth	INTEGER, 
                receiveBandwidth	INTEGER,
                transmitBandwidth	INTEGER,   
--                mdi			INTEGER,
                shutdown		INTEGER,
                loopback    		INTEGER,
                speedDuplex		INTEGER,
                portMode		INTEGER,
                pvid			INTEGER,
                indicatesType		INTEGER,
                vctAction           INTEGER,
                vctLastStatus       DisplayString,
                portTrunkAllowedvlan  OCTET STRING,
                portHybridTaggedAllowedvlan  OCTET STRING,                
                portHybridUntaggedAllowedvlan  OCTET STRING,
                portBandWidthUsage  INTEGER,
                lastFiveMinInPktsPerSec  Counter32,  
                lastFiveMinOutPktsPerSec  Counter32,        
                lastFiveSecInPktsPerSec  Counter32,                 
                lastFiveSecOutPktsPerSec  Counter32,     
                transceiverSn               DisplayString,
                portBlockMode             Counter32, 
                portBlockState            Counter32,
                portComboMediaType  INTEGER,   --add 2015/10/13
				portDiscardPktType		INTEGER
            }

--xxx.100.3.2.1.1
        portIndex OBJECT-TYPE
            SYNTAX  INTEGER
            MAX-ACCESS  read-only
            STATUS  current
            DESCRIPTION
                "port No."
            ::= { priPortEntry 1 }
   

--xxx.100.3.2.1.2
        portName  OBJECT-TYPE
            SYNTAX  DisplayString (SIZE(0..32))
            MAX-ACCESS  read-only
            STATUS  current
            DESCRIPTION
                   " Name of the port. exp:financial."
            ::= { priPortEntry 2 }

            
--xxx.100.3.2.1.3
       switchNum  OBJECT-TYPE
          SYNTAX  INTEGER(0..16)
            MAX-ACCESS  read-only
            STATUS  current
            DESCRIPTION
                   " This value is denoting the number of swith in which this port resides.
                   For the non-stackable device,the value is always 1.
                   While for the stackable device, the value is real switch stack number."
            ::= { priPortEntry 3 }


--xxx.100.3.2.1.4
       slotNum  OBJECT-TYPE
          SYNTAX  INTEGER(0..16)
            MAX-ACCESS  read-only
            STATUS  current
            DESCRIPTION
                   " This value is denoting the number of slot.
                   For the static slot,the value is 1,while for 
                   the extended slot the value is real extended slot number."
            ::= { priPortEntry 4 }


--xxx.100.3.2.1.5
            portType  OBJECT-TYPE
                   SYNTAX      INTEGER
                    {
                        typeSFP(0),
                    	typeCombo(1),
                    	typeFiber(2),
                    	typeSingleOptFE(3),   --modify 04/9/9
                    	typeMultiOptFE(4),
                    	typeElecFE(5),
                    	typeSingleOptGE(6),
                    	typeMultiOptGE(7), 
                    	typeElecGE(8),
                    	typePortAGG(9),
                    	typePortUsbGE(10),
                    	typeOptXge(11),
                    	typeElecXge(12),  -- modify 16/1/11
                        other(255)--modify 03/1/21
                    }
        MAX-ACCESS  read-only
        STATUS      current
        DESCRIPTION "Type of expansion module in this port."
        ::= { priPortEntry 5 }
        
--------------------------------------------------------------------------
-- New requirement begins
--------------------------------------------------------------------------
--xxx.100.3.2.1.6
            flowControlStatus  OBJECT-TYPE
                SYNTAX      INTEGER
                    {
                        disable(0),
                    	enable(1)
                    }
	        MAX-ACCESS  read-write
	        STATUS      current
	        DESCRIPTION 
	        	"The flow-control status of the port. 
	        	Its functionality is exactly same as 'flow control' or 'no flow control' commands
	        	in console mode."
	        ::= { priPortEntry 6 }

--xxx.100.3.2.1.7
            bandwidthControlStatus  OBJECT-TYPE
                SYNTAX      INTEGER
                    {
                         ingress(0),
                    	 egress(1),
                    	 both(2),
                    	 none(3)
                    }
	        MAX-ACCESS  read-only
	        STATUS      current
	        DESCRIPTION 
	        	"The bandwidth-control status of the port. 
	        	Its functionality is to stop the bandwidth control.
	        	The only way to enable bandwidth control is to set receiveBandwidth or transmitBandwith."
	        ::= { priPortEntry 7 }
        
--xxx.100.3.2.1.8
            maxBandwidth  OBJECT-TYPE
                SYNTAX      INTEGER
                	    {
													default(0),
													bw100M(1),
													bw1000M(2),
													bw10000M(3),
													bw40000M(4),
													bw20000M(5),
													bw25G(6),
													bw100G(7)
                	    }
	        MAX-ACCESS  read-only
 	        STATUS      current
	        DESCRIPTION 
	        	"The max bandwidth of the port."
	        ::= { priPortEntry 8 }

--xxx.100.3.2.1.9
            receiveBandwidth  OBJECT-TYPE
                SYNTAX      INTEGER
	        MAX-ACCESS  read-write
 	        STATUS      current
	        DESCRIPTION 
	        	"The recevice bandwidth of the port. Its unit is kbs.
	        	The command 'bandwidth control 50 both' in console mode equals
	        	setting both receiveBandwidth and transmitBandwidth to 50 kbs.
	        	Set 0 is no bandwidth."
	        ::= { priPortEntry 9 }

--xxx.100.3.2.1.10
            transmitBandwidth  OBJECT-TYPE
                SYNTAX      INTEGER
	        MAX-ACCESS  read-write
 	        STATUS      current
	        DESCRIPTION 
	        	"The transmit bandwidth of the port. Its unit is kbs.
	        	Set 0 is no bandwidth."
	        ::= { priPortEntry 10 }
	        
--xxx.100.3.2.1.11
--            mdi  OBJECT-TYPE
--                SYNTAX      INTEGER
--                {
--                        auto(0),
--                    	across(1),
--                    	normal(2)
--                }
--	        MAX-ACCESS  read-write
-- 	        STATUS      current
--	        DESCRIPTION 
--	        	"Establish to specify the on-line type of the port;
--	        	 Exchange the every kind of plank card of machine
--			 of thousand trillion this order of above port nonsupport."
--	        ::= { priPortEntry 11 }

--xxx.100.3.2.1.12
            shutdown  OBJECT-TYPE
                SYNTAX      INTEGER
                {
                        shutDown(0),
                    	noshutdown(1)
                }               
	        MAX-ACCESS  read-write
 	        STATUS      current
	        DESCRIPTION 
	        	"Close or open to specify the port."
	        ::= { priPortEntry 12 }
	        
--xxx.100.3.2.1.13
            loopback  OBJECT-TYPE
                SYNTAX      INTEGER
                {
                        noloopback(0),
                    	loopback(1)
                }                 
	        MAX-ACCESS  read-write
 	        STATUS      current
	        DESCRIPTION 
	        	"Open or close to specify the wreath of 
	        	the port back to test the function."
	        ::= { priPortEntry 13 }	
	        
--xxx.100.3.2.1.14
            speedDuplex  OBJECT-TYPE
                SYNTAX      INTEGER
                {
                        auto(0),
                    	half10(1),
                    	full10(2),
                    	half100(3),
                    	full100(4),
                    	half1000(5),
                    	full1000(6),
                    	half-1000-M(7),
                    	half-1000-s(8),
                    	full-1000-M(9),
                    	full-1000-s(10),
                    	fx-100(13),
                    	fx-100-phy(14),
                    	fx-100-no-phy(15),
                    	neg-10-auto(16),
                    	neg-10-full(17),
                    	neg-10-half(18),
                    	neg-10-100-auto(19),                    	
                    	neg-10-100-full(20), 
                     	neg-10-100-half(21), 
                     	neg-10-100-1000-full(22), 
                     	neg-10-100-1000-half(23),
						neg-full-10g(24),
						full-10g(25),
						full-40g(26)
                    	
                }                                   
	        MAX-ACCESS  read-write
 	        STATUS      current
	        DESCRIPTION 
	        	"The speed and duplex status of the port."
	        ::= { priPortEntry 14 }	
	        
--xxx.100.3.2.1.15
            portMode  OBJECT-TYPE
                SYNTAX      INTEGER
                {
                        access(1),
                    	trunk(2),
                    	hybrid(3)                   	
                }                                   
	        MAX-ACCESS  read-write
 	        STATUS      current
	        DESCRIPTION 
	        	"port mode: 1 is access,2 is trunk,3 is hybrid"
	        ::= { priPortEntry 15 }	
	        
--xxx.100.3.2.1.16
            pvid  OBJECT-TYPE
                SYNTAX      INTEGER                                   
	        MAX-ACCESS  read-write
 	        STATUS      current
	        DESCRIPTION 
	        	"port of native vlan No."
	        ::= { priPortEntry 16 }	
	        
--xxx.100.3.2.1.17
	indicatesType OBJECT-TYPE 
        SYNTAX      INTEGER
                    {
                        other(1),
                        hundredBaseTX(2),
                        hundredBaseFX(3),
                        thousandBaseSX(4),
                        thousandBaseLX(5),
                        thousandBaseT(6),
                        thousandBaseGBIC(7),
                        thousandBaseSfp(8),
                        hundredBaseFxScSingleMode(9),
                        hundredBaseFxScMultiMode(10),
                        thousandBaseCX(11),
                        tenG(12)
                    }
        MAX-ACCESS  read-only
        STATUS      current
        DESCRIPTION "Indicates the port type of the configuration of the switch."
	        ::= { priPortEntry 17 }	
--xxx.100.3.2.1.18
	vctAction OBJECT-TYPE 
        SYNTAX      INTEGER
        MAX-ACCESS  read-write
        STATUS      current
        DESCRIPTION "This object indicates the VCT action of the port,only the value 1 is permitted 
                    when SET this entry though you can GET 1(processing) and 0(succeed);
                    The specified port will be shutdown when one sets 1 to this entry,and then it will return 
                    to no shutdown after operate the virtual-cable-test. You can get the status of VCT from
                    the entry vctLastStatus."
	        ::= { priPortEntry 18 }	  
--xxx.100.3.2.1.19
	vctLastStatus OBJECT-TYPE 
        SYNTAX      DisplayString (SIZE(0..1000))
        MAX-ACCESS  read-only
        STATUS      current
        DESCRIPTION "Indicates the last VCT status of the port."
	        ::= { priPortEntry 19 }	
	        
--xxx.100.3.2.1.20
            portTrunkAllowedvlan  OBJECT-TYPE
            SYNTAX      OCTET STRING
	          MAX-ACCESS  read-write
 	          STATUS      current
	          DESCRIPTION 
	        	"trunk port allowed vlan list string"
	          ::= { priPortEntry 20 }	
	        	               
--xxx.100.3.2.1.21
            portHybridTaggedAllowedvlan  OBJECT-TYPE
            SYNTAX      OCTET STRING
	          MAX-ACCESS  read-write
 	          STATUS      current
	          DESCRIPTION 
	        	"hybrid port tagged allowed vlan list string"
	          ::= { priPortEntry 21 }	
	          
--xxx.100.3.2.1.22
            portHybridUntaggedAllowedvlan  OBJECT-TYPE
            SYNTAX      OCTET STRING
	          MAX-ACCESS  read-write
 	          STATUS      current
	          DESCRIPTION 
	        	"hybrid port untagged allowed vlan list string"
	          ::= { priPortEntry 22 }
	          
--xxx.100.3.2.1.23
            portBandWidthUsage  OBJECT-TYPE
            SYNTAX      INTEGER (0..100)                            
	          MAX-ACCESS  read-only
 	          STATUS      current
	          DESCRIPTION 
	        	"The percentage of the port's bandwidth usage"
	          ::= { priPortEntry 23 }	        

--xxx.100.3.2.1.24
            lastFiveMinInPktsPerSec  OBJECT-TYPE
            SYNTAX      Counter32                            
	          MAX-ACCESS  read-only
 	          STATUS      current
	          DESCRIPTION 
	        	"last five minutes input packets/Sec."
	          ::= { priPortEntry 24 }	   	
	          
--xxx.100.3.2.1.25
            lastFiveMinOutPktsPerSec  OBJECT-TYPE
            SYNTAX      Counter32                            
	          MAX-ACCESS  read-only
 	          STATUS      current
	          DESCRIPTION 
	        	"last five minutes output packets/Sec."
	          ::= { priPortEntry 25 }	 	 
	          
--xxx.100.3.2.1.26
            lastFiveSecInPktsPerSec  OBJECT-TYPE
            SYNTAX      Counter32                            
	          MAX-ACCESS  read-only
 	          STATUS      current
	          DESCRIPTION 
	        	"last five seconds input packets/Sec."
	          ::= { priPortEntry 26 }	     
	          
--xxx.100.3.2.1.27
            lastFiveSecOutPktsPerSec  OBJECT-TYPE
            SYNTAX      Counter32                            
	          MAX-ACCESS  read-only
 	          STATUS      current
	          DESCRIPTION 
	        	"last five seconds output packets/Sec."
	          ::= { priPortEntry 27 }	
--xxx.100.3.2.1.28	          
	          transceiverSn  	   OBJECT-TYPE
            SYNTAX  DisplayString (SIZE(0..16))
            MAX-ACCESS  read-only
            STATUS  current
            DESCRIPTION
                   " serial num of transceiver.if port is not a transceiver,value is null."
	          ::= { priPortEntry 28 }
--xxx.100.3.2.1.29
            portBlockMode  OBJECT-TYPE
            SYNTAX      Counter32                            
	          MAX-ACCESS  read-only
 	          STATUS      current
	          DESCRIPTION 
	        	"port block mode.value:
	        	 noblock:                    0, 
	        	 rate-violation block:       1, 
	        	 loopback-detection block:   2, 
	        	 unknown-protocol block:     3"
	          ::= { priPortEntry 29}
--xxx.100.3.2.1.30
            portBlockState  OBJECT-TYPE
            SYNTAX      Counter32                            
	          MAX-ACCESS  read-only
 	          STATUS      current
	          DESCRIPTION 
	        	"port shutdown mode.value:
	        	 noblock state:                    0, 
	        	 rate-violation block state:       1, 
	        	 loopback-detection block state:   2, 
	        	 unknown-protocol block state:     3"
	          ::= { priPortEntry 30}	
		  
--xxx.100.3.2.1.31		  
 portComboMediaType  OBJECT-TYPE
            SYNTAX      INTEGER 
                        {
                            phyModeCopperPrefered(1),
                            phyModeCopperForced(2),
                            phyModeFiberPrefered(3),
                            phyModeFiberForced(4)
                        }                           
	          MAX-ACCESS  read-write
 	          STATUS      current
	          DESCRIPTION 
	        	"The media type of combo port"
	          ::= { priPortEntry 31 }
--xxx.100.3.2.1.32
portDiscardPktType  OBJECT-TYPE
            SYNTAX      INTEGER
            {
                    tag(1),
					untag(2),
                    no-tag(3),
					no-untag(4)                	
            }                                   
	        MAX-ACCESS  read-write
 	        STATUS      current
	        DESCRIPTION 
	        	"port mode: 1 is tag,2 is untag;
							3 is set no tag,4 is set no untag."
	        ::= { priPortEntry 32 }				  
--********************************************************************************************************
--xxx.100.3.3
stormControlTable OBJECT-TYPE
    SYNTAX  SEQUENCE OF StormControlEntry
    MAX-ACCESS  not-accessible
    STATUS  current
    DESCRIPTION
        "storm-contol table"
    ::= { priPorts   3 }

--xxx.100.3.3.1
    stormControlEntry OBJECT-TYPE
        SYNTAX  StormControlEntry
        MAX-ACCESS  not-accessible
        STATUS  current
        DESCRIPTION
            " storm-control entry"
        INDEX   { stormControlIndex,stormControlType }
        ::= { stormControlTable 1 }

    StormControlEntry
        ::= SEQUENCE
            {
                stormControlIndex   INTEGER,
                stormControlType		INTEGER,
                stormControlRate 		INTEGER,
                stormControlStatus  INTEGER
                      
            }

--xxx.100.3.3.1.1
        stormControlIndex OBJECT-TYPE
            SYNTAX  INTEGER 
            MAX-ACCESS  read-only
            STATUS  current
            DESCRIPTION
                "port index"
            ::= { stormControlEntry 1 }
   

--xxx.100.3.3.1.2
        stormControlType  OBJECT-TYPE
            SYNTAX  INTEGER
            				{
            					broadcast(0),
            					multicast(1),
            					unicast(2),
            					dlf(3),
            					brmc(4),
            					brmcdlf(5),
            					all(6)
            				}
            MAX-ACCESS  read-only
            STATUS  current
            DESCRIPTION
                   "broadcast(broadcast rate suppression),multicast(multicast rate suppression),
                   unicast(unicast rate suppression),dlf(Destination Lookup Failure rate suppression),
                   brmc(broadcast and multicast rate suppression),brmcdlf(Broadcast, multicast and DLF rate suppression)"
            ::= { stormControlEntry 2 }

            
--xxx.100.3.3.1.3
       stormControlRate  OBJECT-TYPE
          SYNTAX  INTEGER
            MAX-ACCESS  read-write
            STATUS  current
            DESCRIPTION
                   "the suppress rate.the value range at <1-1488095> or <1-1000000> on different devices."
            ::= { stormControlEntry 3 }


--xxx.100.3.3.1.4
       stormControlStatus  OBJECT-TYPE
          SYNTAX  INTEGER
          {
          		destroy(0),
          		active(1)
          }
            MAX-ACCESS  read-write
            STATUS  current
            DESCRIPTION
                   "Setting it to  active(1) to creates an entry,setting it to destroy(2) to destroy an entry "
            ::= { stormControlEntry 4 }	                    
--********************************************************************************************************
--******************************************************************************************
--xxx.100.3.4
  loopbackDetection      OBJECT IDENTIFIER ::= { priPorts 4 }
--**************************************************************
--xxx.100.3.4.1   
loopbackDetecCtrlRecovery      OBJECT-TYPE
         SYNTAX             INTEGER (0..3600)
         MAX-ACCESS         read-write
         STATUS              current
         DESCRIPTION        "This value is the state recovery time.When this time comes,
         port back to the normal state.But when the value is 0, does not restore state."
         ::= { loopbackDetection 1 } 

--******************************************************************************************

--xxx.100.3.4.3   
--loopbackDetecInterval  OBJECT IDENTIFIER ::= { loopbackDetection 3 }
--xxx.100.3.4.3.1
--lpbackDetecIntervalStatus  OBJECT-TYPE
--          SYNTAX        INTEGER {
--                                 disable(0),
--                                 enable(1)
--}
--          MAX-ACCESS    read-write
--         STATUS         current
--          DESCRIPTION    "Enable or disable the time interval function of loopback detection."
--          ::= { loopbackDetecInterval 1 }
--xxx.100.3.4.2
loopbackDetecIntervalTime     OBJECT IDENTIFIER ::= { loopbackDetection 2 }
--xxx.100.3.4.2.1
lpbackDetecExistInterval    OBJECT-TYPE
          SYNTAX        INTEGER(5..300)
          MAX-ACCESS    read-write
          STATUS         current
          DESCRIPTION   "This detection time interval is present when the loop exists, 
          in seconds, the range of 5 to 300. The default value is 5."
          ::= { loopbackDetecIntervalTime 1 } 
--xxx.100.3.4.2.2
lpbackDetecNoExistInterval    OBJECT-TYPE
          SYNTAX          INTEGER(1..30)
          MAX-ACCESS      read-write
          STATUS           current
          DESCRIPTION     "This detection time interval is present when the loop does not exist, 
          in seconds, the range from 1 to 30,The default value is 3."
         ::= { loopbackDetecIntervalTime 2 } 
         
--xxx.100.3.4  loopbackDetection  
--xxx.100.3.4.3    
loopbackDetecCtrlTable      OBJECT-TYPE
         SYNTAX             SEQUENCE OF LoopbackDetecCtrlEntry
         MAX-ACCESS         not-accessible
         STATUS             current
         DESCRIPTION        "A table containing current configuration information for
          the function of loopback detection control."
         ::= { loopbackDetection 3 } 
 
--xxx.100.3.4.3.1
loopbackDetecCtrlEntry      OBJECT-TYPE
         SYNTAX            LoopbackDetecCtrlEntry
         MAX-ACCESS        not-accessible
         STATUS            current
         DESCRIPTION       "An entry in the loopback detection control table."
         INDEX            { lpbackDetecCtrlIndex}
         ::= { loopbackDetecCtrlTable 1 }

LoopbackDetecCtrlEntry ::= SEQUENCE
                            {
                             lpbackDetecCtrlIndex    INTEGER,
                             lpbackDetecCtrlMode    INTEGER
 --                          lpbackDetecCtrlStatus    INTEGER
                            }

--xxx.100.3.4.3.1.1  
lpbackDetecCtrlIndex        OBJECT-TYPE
          SYNTAX          INTEGER
          MAX-ACCESS      not-accessible
          STATUS           current
          DESCRIPTION      "An unique value for each port."
          ::={ loopbackDetecCtrlEntry 1 }

--xxx.100.3.4.3.1.2
lpbackDetecCtrlMode      OBJECT-TYPE
          SYNTAX         INTEGER {
                                 nocontrol(0),
                                 shutdown(1),
                                 block(2)
--                               learning control mode has been removed
--                               learning(3)
                                }                       
          MAX-ACCESS      read-write
          STATUS          current
          DESCRIPTION    "Indicates the control type of the configuration of the loopback detection.
          The default value is 0. When the value is set to 0,the loopback detection control function will be disabled."
          ::= { loopbackDetecCtrlEntry 2 }

--xxx.100.3.4.3.1.3
-- lpbackDetecCtrlStatus    OBJECT-TYPE
--         SYNTAX         INTEGER {
--                                  disable(0),
--                                  enable(1)
--                                }
--          MAX-ACCESS     read-only
--         STATUS          current
--          DESCRIPTION    "display the current state of the loopback detection control."
--          ::= { loopbackDetecCtrlEntry 3 }         
--******************************************************************
--xxx.100.3.4.4    
loopbackDetecSpecVlanTable  OBJECT-TYPE
         SYNTAX          SEQUENCE OF LoopbackDetecSpecVlanEntry
         MAX-ACCESS      not-accessible
         STATUS           current
         DESCRIPTION    "Setting the loopback detection function for the specified vlan of the port."
          ::= { loopbackDetection 4 } 

--xxx.100.3.4.4.1
loopbackDetecSpecVlanEntry   OBJECT-TYPE
         SYNTAX            LoopbackDetecSpecVlanEntry
         MAX-ACCESS        not-accessible
         STATUS            current
         DESCRIPTION        "An entry in the loopbackDetecSpecVlanTable."
         INDEX              { lpbackDetecVlanPortIndex }
         ::= { loopbackDetecSpecVlanTable 1 }

LoopbackDetecSpecVlanEntry ::= SEQUENCE
        {
         lpbackDetecVlanPortIndex    INTEGER,
         lpbackDetecVlanList      DisplayString,
         lpbackDetecVlanListSetFlag  INTEGER
--       lpbackDetecVlanStatus    INTEGER
        }
--xxx.100.3.4.4.1.1
lpbackDetecVlanPortIndex     OBJECT-TYPE
          SYNTAX         INTEGER
          MAX-ACCESS      not-accessible
          STATUS          current
          DESCRIPTION    "An unique value for each port."
           ::= { loopbackDetecSpecVlanEntry 1 }
        
--xxx.100.3.4.4.1.2
lpbackDetecVlanList          OBJECT-TYPE
          SYNTAX          DisplayString (SIZE(1..512))
          MAX-ACCESS      read-write
          STATUS           current
          DESCRIPTION      "The value is a vlan list that you will set.Please pay attention to the list of writing,eg:1;3;5-20 ."
          ::= { loopbackDetecSpecVlanEntry 2 }
          
--xxx.100.3.4.4.1.3
lpbackDetecVlanListSetFlag    OBJECT-TYPE
          SYNTAX          INTEGER{
                                  close(0),
                                  open(1)
                                 } 
          MAX-ACCESS      read-write
          STATUS          current
          DESCRIPTION    "When lpbackDetecVlanListSetFlag is 1,open the 
          specified VLAN loopback detection function.When lpbackDetecVlanListSetFlag is 0,close the 
          specified VLAN loopback detection function."
           ::= { loopbackDetecSpecVlanEntry 3 }

--xxx.100.3.4.4.1.3
--lpbackDetecVlanStatus   OBJECT-TYPE
--           SYNTAX     INTEGER{
--                              disable(0),
--                               enable(1)
--                              }
--           MAX-ACCESS  read-write
--          STATUS       current
--           DESCRIPTION   " Enable or disable the loopback detection function for the specified vlan of the port."
--           ::= { loopbackDetecSpecVlanEntry 3 }
--********************************************************************************************************
--xxx.100.3.4.5
loopbackDetecShowTable  OBJECT-TYPE
         SYNTAX          SEQUENCE OF LoopbackDetecShowEntry
         MAX-ACCESS      not-accessible
         STATUS           current
         DESCRIPTION    "Show the config and state of loopback detection for the specified port."
          ::= { loopbackDetection 5 } 
     
--xxx.100.3.4.5.1
loopbackDetecShowEntry   OBJECT-TYPE
         SYNTAX            LoopbackDetecShowEntry
         MAX-ACCESS        not-accessible
         STATUS            current
         DESCRIPTION        "An entry in the loopbackDetecShowTable."
         INDEX              { lpbackDetecShowPortIndex }
         ::= { loopbackDetecShowTable 1 }   
LoopbackDetecShowEntry ::= SEQUENCE
        {
         lpbackDetecShowPortIndex    INTEGER,
         lpbackDetecShowInformation      DisplayString
        }    
--xxx.100.3.4.5.1.1
lpbackDetecShowPortIndex     OBJECT-TYPE
          SYNTAX         INTEGER
          MAX-ACCESS      not-accessible
          STATUS          current
          DESCRIPTION    "An unique value for each port."
           ::= { loopbackDetecShowEntry 1 }
        
--xxx.100.3.4.5.1.2
lpbackDetecShowInformation          OBJECT-TYPE
          SYNTAX          DisplayString (SIZE(1..1024))
          MAX-ACCESS      read-only
          STATUS           current
          DESCRIPTION      "The value display the configuration and state of loopback detection for the specified port."
          ::= { loopbackDetecShowEntry 2 } 
--********************************************************************************************************
--xxx.100.3.5
 stormControlPortTable OBJECT-TYPE
    SYNTAX  SEQUENCE OF StormControlPortEntry
    MAX-ACCESS  not-accessible
    STATUS  current
    DESCRIPTION
        "storm-contol port table"
    ::= { priPorts   5 }
 --xxx.100.3.5.1
    stormControlPortEntry OBJECT-TYPE
        SYNTAX  StormControlPortEntry
        MAX-ACCESS  not-accessible
        STATUS  current
        DESCRIPTION
            " storm-control entry"
        INDEX   { stormControlPortIndex,stormControlSuppressType }
        ::= { stormControlPortTable 1 }

    StormControlPortEntry
        ::= SEQUENCE
            {
                stormControlPortIndex           INTEGER,
                stormControlSuppressType	INTEGER,
                stormControlSuppressRateUnit	INTEGER,
                stormControlSuppressRateValue 	INTEGER,
                stormControlSuppressStatus      INTEGER
                      
            }

--xxx.100.3.5.1.1
        stormControlPortIndex OBJECT-TYPE
            SYNTAX  INTEGER 
            MAX-ACCESS  read-only
            STATUS  current
            DESCRIPTION
                "port index"
            ::= { stormControlPortEntry 1 }
   

--xxx.100.3.5.1.2
        stormControlSuppressType  OBJECT-TYPE
            SYNTAX  INTEGER
            				{
            					broadcast(0),
            					multicast(1),
            					unicast(2)
            				}
            MAX-ACCESS  read-only
            STATUS  current
            DESCRIPTION
                   "broadcast(broadcast rate suppression),multicast(multicast rate suppression),
                   unicast(unicast rate suppression))"
            ::= { stormControlPortEntry 2 }
           
--xxx.100.3.5.1.3
       stormControlSuppressRateUnit  OBJECT-TYPE
          SYNTAX  INTEGER
          {
          	kbps(0),
          	pps(1)
          }
            MAX-ACCESS  read-write
            STATUS  current
            DESCRIPTION
                   "set kbps as measure or set pps as measure "
            ::= { stormControlPortEntry 3 }

--xxx.100.3.5.1.4
       stormControlSuppressRateValue  OBJECT-TYPE
            SYNTAX  INTEGER
            MAX-ACCESS  read-write
            STATUS  current
            DESCRIPTION
                   "if the suppressrate unit is pps,the value range at <1-1488095> ,or if the suppressrate unit is bps,the value range at <1-1000000>,
                   it depends on stormControlSuppressRateUnit."
            ::= { stormControlPortEntry 4 }  
            
--xxx.100.3.5.1.5
       stormControlSuppressStatus  OBJECT-TYPE
          SYNTAX  INTEGER
          {
          	destroy(0),
          	active(1)
          }
            MAX-ACCESS  read-write
            STATUS  current
            DESCRIPTION
                   "Setting it to  active(1) to creates an entry,setting it to destroy(2) to destroy an entry "
            ::= { stormControlPortEntry 5 }	          
--********************************************************************************************************
--xxx.100.3.6
 flowCounterTable OBJECT-TYPE
    SYNTAX  SEQUENCE OF FlowCounterEntry
    MAX-ACCESS  not-accessible
    STATUS  current
    DESCRIPTION
        "control port and vlan interface flow table"
    ::= { priPorts   6 }
 --xxx.100.3.6.1
    flowCounterEntry OBJECT-TYPE
        SYNTAX  FlowCounterEntry
        MAX-ACCESS  not-accessible
        STATUS  current
        DESCRIPTION
            " control port and vlan interface flow entry"
        INDEX   { flowPortIndex,flowVlanID}
        ::= { flowCounterTable 1 }

    FlowCounterEntry
        ::= SEQUENCE
            {    
                flowPortIndex	               INTEGER, 
                flowVlanID                     INTEGER,
                flowCounterInOctets	           Counter64,
                flowCounterInUcastPkts         Counter64,
                flowCounterInMulticastPkts     Counter64,
           		flowCounterInBroadcastPkts     Counter64,
           		flowCounterOutOctets           Counter64,
           		flowCounterOutUcastPkts        Counter64,
           		flowCounterOutMulticastPkts    Counter64,
           		flowCounterOutBroadcastPkts    Counter64,
           		clearFlowCounter               INTEGER
            }
--xxx.100.3.6.1.1   
	flowPortIndex OBJECT-TYPE
	   SYNTAX      INTEGER
       MAX-ACCESS  read-only
       STATUS      current
       DESCRIPTION
               "Port Index"
       ::= { flowCounterEntry 1 }      
--xxx.100.3.6.1.2
	flowVlanID OBJECT-TYPE
	   SYNTAX      INTEGER
       MAX-ACCESS  read-only
       STATUS      current
       DESCRIPTION
               "Vlan ID"
       ::= { flowCounterEntry 2 }    
--xxx.100.3.6.1.3
    flowCounterInOctets OBJECT-TYPE
       SYNTAX      Counter64
       MAX-ACCESS  read-only
       STATUS      current
       DESCRIPTION
               "The total number of octets received on the interface,
               including framing characters.  This object is a 64-bit
               version of ifInOctets."
       ::= { flowCounterEntry 3 } 
--xxx.100.3.6.1.4
    flowCounterInUcastPkts OBJECT-TYPE
       SYNTAX      Counter64
       MAX-ACCESS  read-only
       STATUS      current
       DESCRIPTION
               "The number of packets, delivered by this sub-layer to
               a higher (sub-)layer, which were not addressed to a
               multicast or broadcast address at this sub-layer.
               This object is a 64-bit version of ifInUcastPkts."
       ::= { flowCounterEntry 4 }              
--xxx.100.3.6.1.5     
    flowCounterInMulticastPkts OBJECT-TYPE
       SYNTAX      Counter64
       MAX-ACCESS  read-only
       STATUS      current
       DESCRIPTION
               "The number of packets, delivered by this sub-layer to
               a higher (sub-)layer, which were addressed to a
               multicast address at this sub-layer.  For a MAC layer
               protocol, this includes both Group and Functional
               addresses.  This object is a 64-bit version of   ifInMulticastPkts."
       ::= { flowCounterEntry 5 }
--xxx.100.3.6.1.6
	flowCounterInBroadcastPkts OBJECT-TYPE
       SYNTAX      Counter64
       MAX-ACCESS  read-only
       STATUS      current
       DESCRIPTION
               "The number of packets, delivered by this sub-layer to
               a higher (sub-)layer, which were addressed to a
               broadcast address at this sub-layer.  This object is a
               64-bit version of ifInBroadcastPkts."
       ::= { flowCounterEntry 6 }
--xxx.100.3.6.1.7
	flowCounterOutOctets OBJECT-TYPE
       SYNTAX      Counter64
       MAX-ACCESS  read-only
       STATUS      current
       DESCRIPTION
               "The total number of octets transmitted out of the
               interface, including framing characters.  This object
               is a 64-bit version of ifOutOctets."
       ::= { flowCounterEntry 7 }
--xxx.100.3.6.1.8
    flowCounterOutUcastPkts OBJECT-TYPE
       SYNTAX      Counter64
       MAX-ACCESS  read-only
       STATUS      current
       DESCRIPTION
               "The total number of packets that higher-level
               protocols requested be transmitted, and which were not
               addressed to a multicast or broadcast address at this
               sub-layer, including those that were discarded or not
               sent.  This object is a 64-bit version of
               ifOutUcastPkts."
       ::= { flowCounterEntry 8 }
--xxx.100.3.6.1.9
     flowCounterOutMulticastPkts OBJECT-TYPE
       SYNTAX      Counter64
       MAX-ACCESS  read-only
       STATUS      current
       DESCRIPTION
               "The total number of packets that higher-level
               protocols requested be transmitted, and which were
               addressed to a multicast address at this sub-layer,
               including those that were discarded or not sent.  For
               a MAC layer protocol, this includes both Group and
               Functional addresses.  This object is a 64-bit version   
               of ifOutMulticastPkts."
       ::= { flowCounterEntry 9 }
--xxx.100.3.6.1.10
     flowCounterOutBroadcastPkts OBJECT-TYPE
       SYNTAX      Counter64
       MAX-ACCESS  read-only
       STATUS      current
       DESCRIPTION
               "The total number of packets that higher-level
               protocols requested be transmitted, and which were
               addressed to a broadcast address at this sub-layer,
               including those that were discarded or not sent.  This
               object is a 64-bit version of ifOutBroadcastPkts."
       ::= { flowCounterEntry 10 }   
--xxx.100.3.6.1.11
	clearFlowCounter OBJECT-TYPE 
		SYNTAX    INTEGER
				  {
				  	disable(0),
				  	enable(1)
				  }
		MAX-ACCESS read-write
		STATUS     current
		DESCRIPTION
				"Clear flow counter."
		::={flowCounterEntry 11}  
--********************************************************************************************************  
--xxx.100.3.7
 sumFlowCounterTable OBJECT-TYPE
    SYNTAX  SEQUENCE OF SumFlowCounterEntry
    MAX-ACCESS  not-accessible
    STATUS  current
    DESCRIPTION
        "control port and vlan interface flow table"
    ::= { priPorts   7 }
 --xxx.100.3.7.1
    sumFlowCounterEntry OBJECT-TYPE
        SYNTAX  SumFlowCounterEntry
        MAX-ACCESS  not-accessible
        STATUS  current
        DESCRIPTION
            " control port and vlan interface flow entry"
        INDEX   { sumFlowVlanID}
        ::= { sumFlowCounterTable 1 }

    SumFlowCounterEntry
        ::= SEQUENCE
            {    
                sumFlowVlanID                     INTEGER,
                sumFlowCounterInOctets	           Counter64,
                sumFlowCounterInPkts              Counter64,                
           		sumFlowCounterOutOctets           Counter64,
           		sumFlowCounterOutPkts            Counter64,           		
           		clearSumFlowCounter               INTEGER
            }
--xxx.100.3.7.1.1   
	sumFlowVlanID OBJECT-TYPE
	   SYNTAX      INTEGER
       MAX-ACCESS  read-only
       STATUS      current
       DESCRIPTION
               "Vlan ID"
       ::= { sumFlowCounterEntry 1 }     
--xxx.100.3.7.1.2
    sumFlowCounterInOctets OBJECT-TYPE
       SYNTAX      Counter64
       MAX-ACCESS  read-only
       STATUS      current
       DESCRIPTION
               "The total number of octets received on the interface,
               including framing characters.  This object is a 64-bit
               version of ifInOctets."
       ::= { sumFlowCounterEntry 2 } 

--xxx.100.3.7.1.3   
    sumFlowCounterInPkts OBJECT-TYPE
       SYNTAX      Counter64
       MAX-ACCESS  read-only
       STATUS      current
       DESCRIPTION
               "The number of packets, delivered by this sub-layer to
               a higher (sub-)layer, which were not addressed to a
               multicast or broadcast address at this sub-layer.
               This object is a 64-bit version of ifInUcastPkts."
       ::= { sumFlowCounterEntry 3 }  
           
--xxx.100.3.7.1.4
	sumFlowCounterOutOctets OBJECT-TYPE
       SYNTAX      Counter64
       MAX-ACCESS  read-only
       STATUS      current
       DESCRIPTION
               "The total number of octets transmitted out of the
               interface, including framing characters.  This object
               is a 64-bit version of ifOutOctets."
       ::= { sumFlowCounterEntry 4}
--xxx.100.3.7.1.5
    sumFlowCounterOutPkts OBJECT-TYPE
       SYNTAX      Counter64
       MAX-ACCESS  read-only
       STATUS      current
       DESCRIPTION
               "The total number of packets that higher-level
               protocols requested be transmitted, and which were not
               addressed to a multicast or broadcast address at this
               sub-layer, including those that were discarded or not
               sent.  This object is a 64-bit version of
               ifOutUcastPkts."
       ::= { sumFlowCounterEntry 5 }
--xxx.100.3.7.1.6       
	clearSumFlowCounter OBJECT-TYPE 
		SYNTAX    INTEGER
				  {
				  	disable(0),
				  	enable(1)
				  }
		MAX-ACCESS read-write
		STATUS     current
		DESCRIPTION
				"Clear flow counter."
		::={sumFlowCounterEntry 6}     
--******************************************************************************************************** 
--xxx.100.3.10
        
 portUtilTable OBJECT-TYPE
 	SYNTAX SEQUENCE OF PortUtilEntry
 	MAX-ACCESS not-accessible
 	STATUS current
 	DESCRIPTION
 		"A list of port util entries."
 	::={priPorts  10}
 	
--xxx.100.3.10.1
	portUtilEntry OBJECT-TYPE
		SYNTAX PortUtilEntry
		MAX-ACCESS not-accessible
		STATUS current
		DESCRIPTION
			"A port util entry containing wan port in util,wan port out util,
			bit error rate and packet lost rate." 
		INDEX	{portUtilIndex}
		::= {portUtilTable 1}   
		
	PortUtilEntry
		::= SEQUENCE
			{
				portUtilIndex    INTEGER,
				wanIfInUtil       INTEGER,
				wanIfOutUtil      INTEGER,
				ifBer             INTEGER,
				ifPaketLostRate   INTEGER		
			}  
--xxx.100.3.10.1.1   
	portUtilIndex  OBJECT-TYPE
            SYNTAX  INTEGER (1..1024)
            MAX-ACCESS  read-only
            STATUS  current
            DESCRIPTION
                "port No."
            ::= { portUtilEntry 1 }
--xxx.100.3.10.1.2 
	wanIfInUtil	 OBJECT-TYPE
		SYNTAX	INTEGER 
		MAX-ACCESS read-only
		STATUS	current
		DESCRIPTION
			"WAN port inflows utilization."
		::= {portUtilEntry  2 }
--xxx.100.3.10.1.3
    wanIfOutUtil	 OBJECT-TYPE
		SYNTAX	INTEGER 
		MAX-ACCESS read-only
		STATUS	current
		DESCRIPTION
			"WAN port outflows utilization."
		::= {portUtilEntry  3}

--xxx.100.3.10.1.4   
	 ifBer	 OBJECT-TYPE
		SYNTAX	INTEGER 
		MAX-ACCESS read-only
		STATUS	current
		DESCRIPTION
			"port error rate."
		::= {portUtilEntry  4}

--xxx.100.3.10.1.5
     ifPaketLostRate	OBJECT-TYPE
		SYNTAX	INTEGER 
		MAX-ACCESS read-only
		STATUS	current
		DESCRIPTION
			"port packet lost rate."
		::= {portUtilEntry  5}
	                    
--********************************************************************************************************   
--********************************************************************************************************
--xxx.100.3.11    
portLEDShutoffTable    OBJECT IDENTIFIER ::= { priPorts 11 }
--xxx.100.3.11.1         
portLEDTimerange    OBJECT IDENTIFIER ::= { portLEDShutoffTable 1 }   
--xxx.100.3.11.1.1
portLEDTimeRangeMapTable OBJECT-TYPE
    SYNTAX  SEQUENCE OF PortLEDTimeRangeMapEntry
    MAX-ACCESS  not-accessible
    STATUS  current
            DESCRIPTION
                "timeRange Map Table"
            ::= { portLEDTimerange 1 } 
            
--xxx.100.3.11.1.1.1
    portLEDTimeRangeMapEntry OBJECT-TYPE
        SYNTAX  PortLEDTimeRangeMapEntry
        MAX-ACCESS  not-accessible
        STATUS  current
        DESCRIPTION
            "timeRange Map Entry"
        INDEX   { portLEDTimeRangeMapIndex }
        ::= { portLEDTimeRangeMapTable 1 }

    PortLEDTimeRangeMapEntry
        ::= SEQUENCE
            {
               portLEDTimeRangeMapIndex        INTEGER,
               portLEDTimeRangeMapName		   DisplayString,
               portLEDTimeRangeMapStatus		    INTEGER         
            }
            
--xxx.100.3.11.1.1.1.1
        portLEDTimeRangeMapIndex OBJECT-TYPE
            SYNTAX  INTEGER
            MAX-ACCESS  read-only
            STATUS  current
            DESCRIPTION
                "TimeRange Map index,the range of it is 1-(2^32-1)."
            ::= { portLEDTimeRangeMapEntry 1 }
            
--xxx.100.3.11.1.1.1.2
        portLEDTimeRangeMapName OBJECT-TYPE
            SYNTAX  DisplayString(SIZE (1..64))
            MAX-ACCESS  read-write
            STATUS  current
            DESCRIPTION
                "TimeRange Map name"
            ::= { portLEDTimeRangeMapEntry 2 }

--xxx.100.3.11.1.1.1.3
        portLEDTimeRangeMapStatus OBJECT-TYPE
             SYNTAX  INTEGER
            	    {   
            	       createAndGo(0),         	    	
               		   active(1),
               		   destroy(2)
            	    }
            MAX-ACCESS  read-write
            STATUS  current
            DESCRIPTION
                "TimeRange Map status"
            ::= { portLEDTimeRangeMapEntry 3 }
                                                                       
--xxx.100.3.11.1.1.2
portLEDTimeRangeTable OBJECT-TYPE
    SYNTAX  SEQUENCE OF PortLEDTimeRangeEntry
    MAX-ACCESS  not-accessible
    STATUS  current
            DESCRIPTION
                "timeRange Table"
            ::= { portLEDTimerange 2 } 
                
--xxx.100.3.11.1.1.2.1
    portLEDTimeRangeEntry OBJECT-TYPE
        SYNTAX  PortLEDTimeRangeEntry
        MAX-ACCESS  not-accessible
        STATUS  current
        DESCRIPTION
            "timeRange Entry"
        INDEX   { portLEDTimeRangeIndex,portLEDTimeRangeSubIndex }
        ::= { portLEDTimeRangeTable 1 }

    PortLEDTimeRangeEntry
        ::= SEQUENCE
            {
                portLEDTimeRangeIndex        	INTEGER,
                portLEDTimeRangeSubIndex     	INTEGER,
                portLEDTimeRangeType		    INTEGER,
                portLEDTimeRangeStartWeek		BITS,
                portLEDTimeRangeStartDate		DisplayString,
                portLEDTimeRangeStartTime		DisplayString,  
                portLEDTimeRangeEndWeek	    	BITS,
                portLEDTimeRangeEndDate	    	DisplayString,
                portLEDTimeRangeEndTime	    	DisplayString,             
                portLEDTimeRangeStatus       	INTEGER
            }

--xxx.100.3.11.1.1.2.1.1
        portLEDTimeRangeIndex OBJECT-TYPE
            SYNTAX  INTEGER
            MAX-ACCESS  read-only
            STATUS  current
            DESCRIPTION
                "TimeRange index,the allowed range is 1 to 1000."
            ::= { portLEDTimeRangeEntry 1 }

--xxx.100.3.11.1.1.2.1.2
        portLEDTimeRangeSubIndex OBJECT-TYPE
            SYNTAX  INTEGER
            MAX-ACCESS  read-only
            STATUS  current
            DESCRIPTION
                "TimeRange sub index,the allowed range is 1 to 1000."
            ::= { portLEDTimeRangeEntry 2}
                                  
--xxx.100.3.11.1.1.2.1.3
        portLEDTimeRangeType OBJECT-TYPE
            SYNTAX  INTEGER 
            {
                absolute(1),
                periodic(2)
            }
            MAX-ACCESS  read-write
            STATUS  current
            DESCRIPTION
                "TimeRange type"
            ::= { portLEDTimeRangeEntry 3 }

--xxx.100.3.11.1.1.2.1.4
        portLEDTimeRangeStartWeek OBJECT-TYPE
            SYNTAX  BITS 
                    {
            	    	monday(0),
               		  tuesday(1),
               		  wednesday(2),
            	    	thursday(3),
               		  friday(4),
               		  saturday(5),
               		  sunday(6)               		            	
            	    }
            MAX-ACCESS  read-write
            STATUS  current
            DESCRIPTION
                "configurate the start week,for example: f8 means monday+tuesday+wednesday+thurday+friday,
                the lowest bit is not used,so fe is the biggest."
            ::= { portLEDTimeRangeEntry 4 }

--xxx.100.3.11.1.1.2.1.5
        portLEDTimeRangeStartDate OBJECT-TYPE
            SYNTAX  DisplayString 
            MAX-ACCESS  read-write
            STATUS  current
            DESCRIPTION
                "configurate the start Date,for example YYYY.MM.DD ."
            ::= { portLEDTimeRangeEntry 5 }  
                        
--xxx.100.3.11.1.1.2.1.6
        portLEDTimeRangeStartTime OBJECT-TYPE
            SYNTAX  DisplayString 
            MAX-ACCESS  read-write
            STATUS  current
            DESCRIPTION
                "configurate the start clock,for example HH:MM:SS."
            ::= { portLEDTimeRangeEntry 6}          
--xxx.100.3.11.1.1.2.1.7
        portLEDTimeRangeEndWeek OBJECT-TYPE
            SYNTAX  BITS 
                    {
            	    	monday(0),
               		  tuesday(1),
               		  wednesday(2),
            	    	thursday(3),
               		  friday(4),
               		  saturday(5),
               		  sunday(6)               		            	
            	    }
            MAX-ACCESS  read-write
            STATUS  current
            DESCRIPTION
                "configurate the end week,for example: f8 means monday+tuesday+wednesday+thurday+friday,
                the lowest bit is not used,so fe is the biggest."
            ::= { portLEDTimeRangeEntry 7 }          
--xxx.100.3.11.1.1.2.1.8
        portLEDTimeRangeEndDate OBJECT-TYPE
            SYNTAX  DisplayString 
            MAX-ACCESS  read-write
            STATUS  current
            DESCRIPTION
                "configurate the end date,for example YYYY.MM.DD."
            ::= { portLEDTimeRangeEntry 8 }  
                        
--xxx.100.3.11.1.1.2.1.9
        portLEDTimeRangeEndTime OBJECT-TYPE
            SYNTAX  DisplayString 
            MAX-ACCESS  read-write
            STATUS  current
            DESCRIPTION
                "configurate the end clock,for example HH:MM:SS."
            ::= { portLEDTimeRangeEntry 9 }           
--xxx.100.3.11.1.1.2.1.10
        portLEDTimeRangeStatus OBJECT-TYPE
            SYNTAX  INTEGER
            	    {    
            	     createAndGo(0),       	    	
               		  active(1),
               		  destroy(2)
            	    }
            MAX-ACCESS  read-write
            STATUS  current
            DESCRIPTION
                "status of timeRangeMapTable"
            ::= { portLEDTimeRangeEntry  10 }    
            
--*****************************************************************************************         
--xxx.100.3.11.2   
	portLEDConfig 	OBJECT IDENTIFIER ::= { portLEDShutoffTable 2 } 
--xxx.100.3.11.2.1.1
    portLEDTimeRangeName OBJECT-TYPE
            SYNTAX  DisplayString(SIZE (1..64)) 
            MAX-ACCESS  read-write
            STATUS  current
            DESCRIPTION
                "the timer range of port LED shut-off config"
            ::= { portLEDConfig 1 }
--xxx.100.3.11.2.1.2
	portLEDState  OBJECT-TYPE
            SYNTAX  INTEGER{
            	allOn(0),
                allOff(1)
            }
            MAX-ACCESS  read-only
            STATUS  current
            DESCRIPTION
                   " enable or disable LED shut-off on all ports."
            ::= { portLEDConfig 2 } 
 --xxx.100.3.11.2.1.3
    portLEDTimeRangeDelete OBJECT-TYPE
            SYNTAX  INTEGER{
            	disable(0),
                enable(1)
            }
            MAX-ACCESS  write-only
            STATUS  current
            DESCRIPTION
                "the timer range of port LED shut-off delete"
            ::= { portLEDConfig 3 }  
--********************************************************************************************************  
--xxx.100.3.12
 portTruckAllowedVlanTable OBJECT-TYPE
    SYNTAX  SEQUENCE OF PortTruckAllowedVlanEntry
    MAX-ACCESS  not-accessible
    STATUS  current
    DESCRIPTION
        "Truck port alllowed vlan table"
    ::= { priPorts   12 }
 --xxx.100.3.12.1
    portTruckAllowedVlanEntry OBJECT-TYPE
        SYNTAX  PortTruckAllowedVlanEntry
        MAX-ACCESS  not-accessible
        STATUS  current
        DESCRIPTION
            " Truck port alllowed vlan entry"
        INDEX   {portTruckPortIndex}
        ::= { portTruckAllowedVlanTable 1 }

    PortTruckAllowedVlanEntry
        ::= SEQUENCE
            {    
                portTruckPortIndex                   INTEGER,
                portTruckAllowedVlan	             OCTET STRING,
                portTruckAllowedVlanAdd              OCTET STRING, 
           		portTruckAllowedVlanExcept           OCTET STRING,   
           		portTruckAllowedVlanRemove           OCTET STRING,
           		portTruckAllowedVlanAll              INTEGER 
            }
--xxx.100.3.12.1.1   
	portTruckPortIndex OBJECT-TYPE
	   SYNTAX      INTEGER
       MAX-ACCESS  not-accessible
       STATUS      current
       DESCRIPTION
               "port index of truck mode"
       ::= { portTruckAllowedVlanEntry 1 }     
--xxx.100.3.12.1.2
    portTruckAllowedVlan OBJECT-TYPE
       SYNTAX      OCTET STRING
       MAX-ACCESS  read-write
       STATUS      current
       DESCRIPTION
               "VLAN IDs of the allowed VLANs when this port is in trunking mode."
       ::= { portTruckAllowedVlanEntry 2 } 

--xxx.100.3.12.1.3   
    portTruckAllowedVlanAdd OBJECT-TYPE
       SYNTAX      OCTET STRING
       MAX-ACCESS  read-write
       STATUS      current
       DESCRIPTION
               "Add VLANs to the current list."
       ::= { portTruckAllowedVlanEntry 3 }  
           
--xxx.100.3.12.1.4
	portTruckAllowedVlanExcept OBJECT-TYPE
       SYNTAX      OCTET STRING
       MAX-ACCESS  read-write
       STATUS      current
       DESCRIPTION
               "All VLANs except the following."
       ::= { portTruckAllowedVlanEntry 4}
--xxx.100.3.12.1.5
    portTruckAllowedVlanRemove OBJECT-TYPE
       SYNTAX      OCTET STRING
       MAX-ACCESS  read-write
       STATUS      current
       DESCRIPTION
               "Remove VLANs from the current list."
       ::= { portTruckAllowedVlanEntry 5 }
--xxx.100.3.12.1.6       
	portTruckAllowedVlanAll OBJECT-TYPE 
		SYNTAX    INTEGER
				  {
				  	none(0),
				  	all(1)
				  }
		MAX-ACCESS read-write
		STATUS     current
		DESCRIPTION
				"Allow all(1) vlans or none vlans."
		::={portTruckAllowedVlanEntry 6}   
--********************************************************************************************************  
--xxx.100.3.13
 portHybridTaggedAllowedVlanTable OBJECT-TYPE
    SYNTAX  SEQUENCE OF PortHybridTaggedAllowedVlanEntry
    MAX-ACCESS  not-accessible
    STATUS  current
    DESCRIPTION
        "Truck port alllowed vlan table"
    ::= { priPorts   13 }
 --xxx.100.3.13.1
    portHybridTaggedAllowedVlanEntry OBJECT-TYPE
        SYNTAX  PortHybridTaggedAllowedVlanEntry
        MAX-ACCESS  not-accessible
        STATUS  current
        DESCRIPTION
            " Truck port alllowed vlan entry"
        INDEX   { portHybridTaggedPortIndex }
        ::= { portHybridTaggedAllowedVlanTable 1 }

    PortHybridTaggedAllowedVlanEntry
        ::= SEQUENCE
            {    
                portHybridTaggedPortIndex                   INTEGER,
                portHybridTaggedAllowedVlan	              OCTET STRING,
                portHybridTaggedAllowedVlanAdd              OCTET STRING, 
           		portHybridTaggedAllowedVlanExcept           OCTET STRING,   
           		portHybridTaggedAllowedVlanRemove           OCTET STRING,
           		portHybridTaggedAllowedVlanAll              INTEGER 
            }
--xxx.100.3.13.1.1   
	portHybridTaggedPortIndex OBJECT-TYPE
	   SYNTAX      INTEGER
       MAX-ACCESS  not-accessible
       STATUS      current
       DESCRIPTION
               "port index of Hybrid mode"
       ::= { portHybridTaggedAllowedVlanEntry 1 }     
--xxx.100.3.13.1.2
    portHybridTaggedAllowedVlan OBJECT-TYPE
       SYNTAX      OCTET STRING
       MAX-ACCESS  read-write
       STATUS      current
       DESCRIPTION
               "VLAN IDs of the allowed VLANs when this port is in hybrid mode."
       ::= { portHybridTaggedAllowedVlanEntry 2 } 

--xxx.100.3.13.1.3   
    portHybridTaggedAllowedVlanAdd OBJECT-TYPE
       SYNTAX      OCTET STRING
       MAX-ACCESS  read-write
       STATUS      current
       DESCRIPTION
               "Add VLANs to the current list."
       ::= { portHybridTaggedAllowedVlanEntry 3 }  
           
--xxx.100.3.13.1.4
	portHybridTaggedAllowedVlanExcept OBJECT-TYPE
       SYNTAX      OCTET STRING
       MAX-ACCESS  read-write
       STATUS      current
       DESCRIPTION
               "All VLANs except the following."
       ::= { portHybridTaggedAllowedVlanEntry 4}
--xxx.100.3.13.1.5
    portHybridTaggedAllowedVlanRemove OBJECT-TYPE
       SYNTAX      OCTET STRING
       MAX-ACCESS  read-write
       STATUS      current
       DESCRIPTION
               "Remove VLANs from the current list."
       ::= { portHybridTaggedAllowedVlanEntry 5 }
--xxx.100.3.13.1.6       
	portHybridTaggedAllowedVlanAll OBJECT-TYPE 
		SYNTAX    INTEGER
				  {
				  	none(0),
				  	all(1)
				  }
		MAX-ACCESS read-write
		STATUS     current
		DESCRIPTION
				"allow all(1) vlans or none vlans."
		::={portHybridTaggedAllowedVlanEntry 6}            
--****************************************************************************************************************** 
--********************************************************************************************************  
--xxx.100.3.14
 portHybridUntaggedAllowedVlanTable OBJECT-TYPE
    SYNTAX  SEQUENCE OF PortHybridUntaggedAllowedVlanEntry
    MAX-ACCESS  not-accessible
    STATUS  current
    DESCRIPTION
        "Truck port alllowed vlan table"
    ::= { priPorts   14 }
 --xxx.100.3.14.1
    portHybridUntaggedAllowedVlanEntry OBJECT-TYPE
        SYNTAX  PortHybridUntaggedAllowedVlanEntry
        MAX-ACCESS  not-accessible
        STATUS  current
        DESCRIPTION
            " Truck port alllowed vlan entry"
        INDEX   { portHybridUntaggedPortIndex }
        ::= { portHybridUntaggedAllowedVlanTable 1 }

    PortHybridUntaggedAllowedVlanEntry
        ::= SEQUENCE
            {    
                portHybridUntaggedPortIndex                   INTEGER,
                portHybridUntaggedAllowedVlan	              OCTET STRING,
                portHybridUntaggedAllowedVlanAdd              OCTET STRING, 
           		portHybridUntaggedAllowedVlanExcept           OCTET STRING,   
           		portHybridUntaggedAllowedVlanRemove           OCTET STRING,
           		portHybridUntaggedAllowedVlanAll              INTEGER 
            }
--xxx.100.3.14.1.1   
	portHybridUntaggedPortIndex OBJECT-TYPE
	   SYNTAX      INTEGER
       MAX-ACCESS  not-accessible
       STATUS      current
       DESCRIPTION
               "port index of Hybrid mode"
       ::= { portHybridUntaggedAllowedVlanEntry 1 }     
--xxx.100.3.14.1.2
    portHybridUntaggedAllowedVlan OBJECT-TYPE
       SYNTAX      OCTET STRING
       MAX-ACCESS  read-write
       STATUS      current
       DESCRIPTION
               "VLAN IDs of the allowed VLANs when this port is in hybrid mode."
       ::= { portHybridUntaggedAllowedVlanEntry 2 } 

--xxx.100.3.14.1.3   
    portHybridUntaggedAllowedVlanAdd OBJECT-TYPE
       SYNTAX      OCTET STRING
       MAX-ACCESS  read-write
       STATUS      current
       DESCRIPTION
               "Add VLANs to the current list."
       ::= { portHybridUntaggedAllowedVlanEntry 3 }  
           
--xxx.100.3.14.1.4
	portHybridUntaggedAllowedVlanExcept OBJECT-TYPE
       SYNTAX      OCTET STRING
       MAX-ACCESS  read-write
       STATUS      current
       DESCRIPTION
               "All VLANs except the following."
       ::= { portHybridUntaggedAllowedVlanEntry 4}
--xxx.100.3.14.1.5
    portHybridUntaggedAllowedVlanRemove OBJECT-TYPE
       SYNTAX      OCTET STRING
       MAX-ACCESS  read-write
       STATUS      current
       DESCRIPTION
               "Remove VLANs from the current list."
       ::= { portHybridUntaggedAllowedVlanEntry 5 }
--xxx.100.3.14.1.6       
	portHybridUntaggedAllowedVlanAll OBJECT-TYPE 
		SYNTAX    INTEGER
				  {
				  	none(0),
				  	all(1)
				  }
		MAX-ACCESS read-write
		STATUS     current
		DESCRIPTION
				"allow all(1) vlans or none vlans."
		::={portHybridUntaggedAllowedVlanEntry 6}            
--******************************************************************************************************************
--xxx.100.4  priIpConfig

--***************************************

--xxx.100.4.1
            netDefaultGateway  OBJECT-TYPE
                SYNTAX      IpAddress            
	        MAX-ACCESS  read-write
 	        STATUS      current
	        DESCRIPTION 
	        	"The IP Address of the default gateway.  If this value is
        		undefined or unknown, it shall have the value 0.0.0.0."
	        ::= { priIpConfig 1 }

--xxx.100.4.2
            ipHttpState  OBJECT-TYPE
                SYNTAX      INTEGER
                {
                        disable(0),
                    	enable(1)
                }                         
	        MAX-ACCESS  read-write
 	        STATUS      current
	        DESCRIPTION 
	        	"Web server on-off."
	        ::= { priIpConfig 2 }
	        
--xxx.100.4.3
iPAddrTable OBJECT-TYPE
        SYNTAX      SEQUENCE OF IPAddrEntry
        MAX-ACCESS  not-accessible
        STATUS      current
        DESCRIPTION "A table of iPAddrEntry."
        ::= { priIpConfig 3 }

--xxx.100.4.3.1
iPAddrEntry OBJECT-TYPE
        SYNTAX      IPAddrEntry
        MAX-ACCESS  not-accessible
        STATUS      current
        DESCRIPTION "A set of configuration parameters for a particular
        network interface on this device. If the device has no network
        interface, this table is empty.

        The index is composed of the ifIndex assigned to the
        corresponding interface."
        INDEX   { iPAddrVid , iPAddrIPAddress }
        ::= { iPAddrTable 1 }

IPAddrEntry ::= SEQUENCE
{
    iPAddrVid               	INTEGER,
    iPAddrIPAddress             IpAddress,
    iPAddrSubnetMask     	IpAddress,
    iPAddrPrimaryInterface      INTEGER,
    iPAddrStatus		INTEGER
}
--xxx.100.4.3.1.1
iPAddrVid  OBJECT-TYPE
    SYNTAX     INTEGER
    MAX-ACCESS not-accessible
    STATUS     current
    DESCRIPTION "The VLAN interface being used by this table entry. Only the 
                 VLAN interfaces which have an IP configured will appear in
                 the table."
    ::= { iPAddrEntry 1 }
    
--xxx.100.4.3.1.2   
iPAddrIPAddress  OBJECT-TYPE
    SYNTAX     IpAddress
    MAX-ACCESS not-accessible
    STATUS     current
    DESCRIPTION
        "The IP address of this Net interface.  The default value
        for this object is 0.0.0.0.  If either the IPAddrIPAddress
        or IPAddrSubnetMask is 0.0.0.0, then when the device
        boots, it may use BOOTP to try to figure out what these
        values should be. If BOOTP fails, before the device
        can talk on the network, this value must be configured
        (e.g., through a terminal attached to the device)."
    ::= { iPAddrEntry 2 }

--xxx.100.4.3.1.3
iPAddrSubnetMask  OBJECT-TYPE
    SYNTAX     IpAddress
    MAX-ACCESS read-create
    STATUS     current
    DESCRIPTION
        "The subnet mask of this Net interface.  The default value
        for this object is 0.0.0.0.  If either the IPAddrIPAddress
        or IPAddrSubnetMask are 0.0.0.0, then when the device
        boots, it may use BOOTP to try to figure out what these
        values should be. If BOOTP fails, before the device
        can talk on the network, this value must be configured
        (e.g., through a terminal attached to the device)."
    ::= { iPAddrEntry 3 }

--xxx.100.4.3.1.4
iPAddrPrimaryInterface OBJECT-TYPE
    SYNTAX     INTEGER
               {
                   primary(0),
                   secondary(1)
               }
    MAX-ACCESS read-create
    STATUS     current
    DESCRIPTION
        "Whether this is a primary interface."
    ::= { iPAddrEntry 4 }
 
--xxx.100.4.3.1.5
iPAddrStatus OBJECT-TYPE
    SYNTAX     INTEGER
               {
            	   createAndGo(0),
               	   active(1),
               	   destroy(2)
               }
    MAX-ACCESS read-create
    STATUS     current
    DESCRIPTION
        "Now state."
    ::= { iPAddrEntry 5 }        

--********************************************************************************************************

--xxx.100.4.4
interfaceTable OBJECT-TYPE
        SYNTAX      SEQUENCE OF InterfaceEntry
        MAX-ACCESS  not-accessible
        STATUS      current
        DESCRIPTION "A table of interfaceEntry."
        ::= { priIpConfig 4 }

--xxx.100.5.1.1
interfaceEntry OBJECT-TYPE
        SYNTAX      InterfaceEntry
        MAX-ACCESS  not-accessible
        STATUS      current
        DESCRIPTION "A set of configuration parameters for a particular
        network interface on this device. If the device has no network
        interface, this table is empty.

        The index is composed of the ifIndex assigned to the
        corresponding interface."
        INDEX   { intfacetype , intfaceID }
        ::= { interfaceTable 1 }

InterfaceEntry ::= SEQUENCE
{
    intfacetype               	INTEGER,
    intfaceID    		INTEGER,
    intfaceIndex     		INTEGER,
--  intfaceAddressMethod      	INTEGER,
    intfaceStatus		INTEGER
}

intfacetype  OBJECT-TYPE
    SYNTAX     INTEGER
               {
                    vintf(1),
                    loopback(2),
                    tunnel(3)
               }
    MAX-ACCESS not-accessible
    STATUS     current
    DESCRIPTION "The Type of interface.
                 Now support(1)vintf and (2)loopback."
    ::= { interfaceEntry 1 }
    
intfaceID  OBJECT-TYPE
    SYNTAX     INTEGER
    MAX-ACCESS not-accessible
    STATUS     current
    DESCRIPTION
        "The Number of interface.
        exp:intfacetype(1),interfaceID(2) means interface vlan 2.
            if intfacetype(2) interfaceID(4) means interface loopback4.
            if intfacetype(3) interfaceID(5) means interface Tunnel5."
    ::= { interfaceEntry 2 }

intfaceIndex  OBJECT-TYPE
    SYNTAX     INTEGER
    MAX-ACCESS read-only
    STATUS     current
    DESCRIPTION
        "The Index of interface."
    ::= { interfaceEntry 3 }

--intfaceAddressMethod OBJECT-TYPE
--    SYNTAX     INTEGER
--               {
--                    user(0),
--                    dhcp(1),
--                    bootp(2)
--               }
--    MAX-ACCESS read-create
--    STATUS     current
--    DESCRIPTION
--        "Method to get the IP address. 
--        When intfacetype(2/3) intfaceAddressMethod must be user()."
--    ::= { interfaceEntry 4 }

intfaceStatus OBJECT-TYPE
    SYNTAX     INTEGER
               {
            	   createAndGo(0),
               	   active(1),
               	   destroy(2)
               }
    MAX-ACCESS read-create
    STATUS     current
    DESCRIPTION
        "Now state."
    ::= { interfaceEntry 5 }  


	        	                                    
--********************************************************************************************************
--******************************************************************************************************** 

--xxx.100.5  vlanConfig

--***************************************
--vlaninfotable
--***************************************

--xxx.100.5.1
vlanInfoTable OBJECT-TYPE
        SYNTAX      SEQUENCE OF VlanInfoEntry
        MAX-ACCESS  not-accessible
        STATUS      current
        DESCRIPTION "A table containing current configuration information
        for each VLAN currently configured into the device by
        (local or network) management."
        ::= { priVlanConfig 1 }

--xxx.100.5.1.1
vlanInfoEntry OBJECT-TYPE
        SYNTAX      VlanInfoEntry
        MAX-ACCESS  not-accessible
        STATUS      current
        DESCRIPTION "Static information for a VLAN configured into the
        device by (local or network) management."
        INDEX   { vlanID }
        ::= { vlanInfoTable 1 }

VlanInfoEntry ::= SEQUENCE
{
    vlanID             INTEGER,
    vlanName           DisplayString,
    vlanPortNumber     INTEGER,
    vlanRowStatus      INTEGER
}

        
--xxx.100.5.1.1.1
vlanID OBJECT-TYPE
        SYNTAX      INTEGER (1..4094)
        MAX-ACCESS  not-accessible
        STATUS      current
        DESCRIPTION "This value is vlan's ID."
        ::= { vlanInfoEntry 1 }

--xxx.100.5.1.1.2
vlanName OBJECT-TYPE
        SYNTAX      DisplayString (SIZE (1..64))
        MAX-ACCESS  read-create
        STATUS      current
        DESCRIPTION "which may be used to identify the VLAN."
        ::= { vlanInfoEntry 2 }

--xxx.100.5.1.1.3
vlanPortNumber OBJECT-TYPE
        SYNTAX      INTEGER (0..65535)
        MAX-ACCESS  read-only
        STATUS      current
        DESCRIPTION "The sum of vlan's ports."
        ::= { vlanInfoEntry 3 }

--xxx.100.5.1.1.4
vlanRowStatus OBJECT-TYPE
    SYNTAX      INTEGER
    		{
               	   active(1),
               	   destroy(2)    		
    		}
    MAX-ACCESS  read-create
    STATUS      current
    DESCRIPTION
        "This object indicates the status of this entry."
    ::= { vlanInfoEntry 4 }        
    
--********************************************************************************************************
--********************************************************************************************************
 --MvlanConfig
--***************************************
--xxx.100.5.2 
--***************************************
mvlanInfoTable OBJECT-TYPE
        SYNTAX      SEQUENCE OF MvlanInfoEntry
        MAX-ACCESS  not-accessible
        STATUS      current
        DESCRIPTION "A table containing current configuration information
        for  Multicast VLAN ."
        ::= {priVlanConfig 2  }

--xxx.100.5.2.1
mvlanInfoEntry OBJECT-TYPE
        SYNTAX      MvlanInfoEntry
        MAX-ACCESS  not-accessible
        STATUS      current
        DESCRIPTION "Static information for Multicast VLAN configured into the
        device by (local or network) management."
        INDEX   { mvlanID }
        ::= { mvlanInfoTable 1 }
MvlanInfoEntry ::= SEQUENCE
{
    mvlanID            INTEGER,
    mvlanStatus        INTEGER,
    mvlanAssoVlanList  DisplayString,
    mvlanAssoVlanStatus INTEGER, 
    mvlanMode          INTEGER
}
--xxx.100.5.2.1.1
mvlanID OBJECT-TYPE
        SYNTAX      INTEGER (1..4094)
        MAX-ACCESS  not-accessible
        STATUS      current
        DESCRIPTION "This value is mvlan's ID."
        ::= { mvlanInfoEntry 1 }
--xxx.100.5.2.1.2        
mvlanStatus OBJECT-TYPE
    SYNTAX      INTEGER
    		{
               	   enable(1),  
               	   disable(0)    		
    		}
    MAX-ACCESS  read-write
    STATUS      current
    DESCRIPTION "the status of mVLAN:enable(1) to active a mvlanID;disable(0) is to destroy a mvlanID."
     ::= {mvlanInfoEntry 2 } 
--xxx.100.5.2.1.3
mvlanAssoVlanList OBJECT-TYPE
SYNTAX  DisplayString (SIZE(1..100)) 
            MAX-ACCESS  read-write
            STATUS  current
            DESCRIPTION
                " configure vlans association with multicast Vlan,such as'3-4'or '2,5,6',set or unset by Configuring mvlanAssoVlanStatus; geting vlans which associating with multicast Vlan ."
            ::= {mvlanInfoEntry 3} 
--xxx.100.5.2.1.4        
mvlanAssoVlanStatus OBJECT-TYPE
    SYNTAX      INTEGER
    		{
               	   enable(1),  
               	   disable(0)    		
    		}
    MAX-ACCESS  read-write
    STATUS      current
    DESCRIPTION "the status of mvlanAssoVlan:enable(1) to enable multicast Vlan association with Vlan;
        disable(0) is to disable multicast Vlan association with  Vlan."
     ::= {mvlanInfoEntry 4 } 
--xxx.100.5.2.1.5
mvlanMode OBJECT-TYPE
SYNTAX  INTEGER
  	    {
  	    	default(0),
  	    	dynamic(1),
     		  compatible(2)
  	    }
  MAX-ACCESS  read-write
  STATUS  current
  DESCRIPTION
      "configure mode: when no configration,Default: 0."
  ::= {mvlanInfoEntry 5}  
--xxx.100.5.3  
mvlanPortInfoTable OBJECT-TYPE
        SYNTAX      SEQUENCE OF MvlanPortInfoEntry
        MAX-ACCESS  not-accessible
        STATUS      current
        DESCRIPTION "A table containing current configuration information
        for each Multicast VLAN ."
        ::= { priVlanConfig 3  }
--xxx.100.5.3.1
mvlanPortInfoEntry OBJECT-TYPE
        SYNTAX      MvlanPortInfoEntry
        MAX-ACCESS  not-accessible
        STATUS      current
        DESCRIPTION "Static information for Multicast VLAN configured into the
        device by (local or network) management."
        INDEX   { mvlanVId,mvlanPortIndex }
        ::= { mvlanPortInfoTable 1 }
MvlanPortInfoEntry ::= SEQUENCE
{
    mvlanVId           INTEGER,
    mvlanPortIndex     INTEGER,
    mvlanAssoPortTagid INTEGER,
    mvlanPortStatus    INTEGER      
}
--xxx.100.5.3.1.1
mvlanVId OBJECT-TYPE
        SYNTAX      INTEGER (1..4094)
        MAX-ACCESS  not-accessible
        STATUS      current
        DESCRIPTION "This value is mvlan's ID."
        ::= { mvlanPortInfoEntry 1 }
--xxx.100.5.3.1.2          
mvlanPortIndex OBJECT-TYPE
        SYNTAX      INTEGER
        MAX-ACCESS  not-accessible
        STATUS      current
        DESCRIPTION 
            "Mvlan's port index."
        ::= { mvlanPortInfoEntry 2 }
--xxx.100.5.3.1.3
mvlanAssoPortTagid   OBJECT-TYPE
SYNTAX      INTEGER (1..4094)	
        MAX-ACCESS  read-write
        STATUS      current
        DESCRIPTION "tagId of portIndex association with multicast Vlan,Default:0.if port needn't Tagid,
          set portIndex association with mvlanVId only."
        ::= {mvlanPortInfoEntry 3 }         
--xxx.100.5.3.1.4
mvlanPortStatus OBJECT-TYPE
    SYNTAX      INTEGER
    		{
               	   enable(1),  
               	   disable(0)    		
    		}
    MAX-ACCESS  read-write
    STATUS      current
    DESCRIPTION "the status of mvlanPortStatus:enable(1) to enable port association with multicast Vlan;
        disable(0) is to disable port association with multicast Vlan."
     ::= {mvlanPortInfoEntry 4 }  
--*******************************************************************************************************
--*******************************************************************************************************          
--xxx.100.5.4        
vlanFlowCounterTable OBJECT-TYPE
        SYNTAX      SEQUENCE OF VlanFlowCounterEntry
        MAX-ACCESS  not-accessible
        STATUS      current
        DESCRIPTION "A table containing flow counters according to vlanid,in/out direction,
        containing unicast,multicast and broadcast flow."
        ::= { priVlanConfig 4 }
--xxx.100.5.4.1
vlanFlowCounterEntry OBJECT-TYPE
        SYNTAX      VlanFlowCounterEntry
        MAX-ACCESS  not-accessible
        STATUS      current
        DESCRIPTION "Flow counters on vlan for in/out ports."
        INDEX   { vlanID }
        ::= { vlanFlowCounterTable 1 }

VlanFlowCounterEntry ::= SEQUENCE
{
    vlanFCVlanID      INTEGER,
    vlanInOctets           Counter64,
    vlanInUcastPkts        Counter64,
    vlanInMulticastPkts    Counter64,
    vlanInBroadcastPkts    Counter64,
    vlanOutOctets          Counter64,
    vlanOutUcastPkts       Counter64,
    vlanOutMulticastPkts   Counter64,
    vlanOutBroadcastPkts   Counter64,
    clearVlanFlowCounter   INTEGER
}

        
--xxx.100.5.4.1.1
vlanFCVlanID OBJECT-TYPE
        SYNTAX      INTEGER (1..4094)
        MAX-ACCESS  not-accessible
        STATUS      current
        DESCRIPTION "This value is vlan's ID."
        ::= { vlanFlowCounterEntry 1 }

--xxx.100.5.4.1.2
    vlanInOctets OBJECT-TYPE
       SYNTAX      Counter64
       MAX-ACCESS  read-only
       STATUS      current
       DESCRIPTION
               "The total number of octets received on the interface,
               including framing characters.  This object is a 64-bit
               version of ifInOctets."
       ::= { vlanFlowCounterEntry 2 } 
--xxx.100.5.4.1.3
    vlanInUcastPkts OBJECT-TYPE
       SYNTAX      Counter64
       MAX-ACCESS  read-only
       STATUS      current
       DESCRIPTION
               "The number of packets, delivered by this sub-layer to
               a higher (sub-)layer, which were not addressed to a
               multicast or broadcast address at this sub-layer.
               This object is a 64-bit version of ifInUcastPkts."
       ::= { vlanFlowCounterEntry 3 }              
--xxx.100.5.4.1.4     
    vlanInMulticastPkts OBJECT-TYPE
       SYNTAX      Counter64
       MAX-ACCESS  read-only
       STATUS      current
       DESCRIPTION
               "The number of packets, delivered by this sub-layer to
               a higher (sub-)layer, which were addressed to a
               multicast address at this sub-layer.  For a MAC layer
               protocol, this includes both Group and Functional
               addresses.  This object is a 64-bit version of   ifInMulticastPkts."
       ::= { vlanFlowCounterEntry 4 }
--xxx.100.5.4.1.5	
	vlanInBroadcastPkts OBJECT-TYPE
       SYNTAX      Counter64
       MAX-ACCESS  read-only
       STATUS      current
       DESCRIPTION
               "The number of packets, delivered by this sub-layer to
               a higher (sub-)layer, which were addressed to a
               broadcast address at this sub-layer.  This object is a
               64-bit version of ifInBroadcastPkts."
       ::= { vlanFlowCounterEntry 5 }
--xxx.100.5.4.1.6	
	vlanOutOctets OBJECT-TYPE
       SYNTAX      Counter64
       MAX-ACCESS  read-only
       STATUS      current
       DESCRIPTION
               "The total number of octets transmitted out of the
               interface, including framing characters.  This object
               is a 64-bit version of ifOutOctets."
       ::= { vlanFlowCounterEntry 6 }
--xxx.100.5.4.1.7    
	vlanOutUcastPkts OBJECT-TYPE
       SYNTAX      Counter64
       MAX-ACCESS  read-only
       STATUS      current
       DESCRIPTION
               "The total number of packets that higher-level
               protocols requested be transmitted, and which were not
               addressed to a multicast or broadcast address at this
               sub-layer, including those that were discarded or not
               sent.  This object is a 64-bit version of
               ifOutUcastPkts."
       ::= { vlanFlowCounterEntry 7 }
--xxx.100.5.4.1.8
     vlanOutMulticastPkts OBJECT-TYPE
       SYNTAX      Counter64
       MAX-ACCESS  read-only
       STATUS      current
       DESCRIPTION
               "The total number of packets that higher-level
               protocols requested be transmitted, and which were
               addressed to a multicast address at this sub-layer,
               including those that were discarded or not sent.  For
               a MAC layer protocol, this includes both Group and
               Functional addresses.  This object is a 64-bit version   
               of ifOutMulticastPkts."
       ::= { vlanFlowCounterEntry 8 }
--xxx.100.5.4.1.9
     vlanOutBroadcastPkts OBJECT-TYPE
       SYNTAX      Counter64
       MAX-ACCESS  read-only
       STATUS      current
       DESCRIPTION
               "The total number of packets that higher-level
               protocols requested be transmitted, and which were
               addressed to a broadcast address at this sub-layer,
               including those that were discarded or not sent.  This
               object is a 64-bit version of ifOutBroadcastPkts."
       ::= { vlanFlowCounterEntry 9 }   
--xxx.100.5.4.1.10
	clearVlanFlowCounter OBJECT-TYPE 
		SYNTAX    INTEGER
				  {
				  	disable(0),
				  	enable(1)
				  }
		MAX-ACCESS read-write
		STATUS     current
		DESCRIPTION
				"Clear flow counter."
		::={vlanFlowCounterEntry 10}    
   
--*****************************************************************************************           
--*****************************************************************************************         
--xxx.100.6 jumblyStacking

--xxx.100.6.1
sysStackUnitNumber OBJECT-TYPE
    SYNTAX  INTEGER
    MAX-ACCESS  read-only
    STATUS  current
    DESCRIPTION
        " the number of the stacked units."
    ::= { priJumblyStacking  1 } 
               
--xxx.100.6.2
jumblyStackingInfoTable OBJECT-TYPE
        SYNTAX      SEQUENCE OF JumblyStackingInfoEntry
        MAX-ACCESS  not-accessible
        STATUS      current
        DESCRIPTION "Table of descriptive and status information about
                     jumbly stacking in this system."
        ::= { priJumblyStacking 2 }
          
--xxx.100.6.1.1
jumblyStackingInfoEntry OBJECT-TYPE
        SYNTAX      JumblyStackingInfoEntry
        MAX-ACCESS  not-accessible
        STATUS      current
        DESCRIPTION "An entry in the table, containing information
                     about stacking switch in this system."
        INDEX       { swUnitIndex }
        ::= { jumblyStackingInfoTable 1 }

JumblyStackingInfoEntry ::= SEQUENCE
{
    stackingUnitIndex        INTEGER,
    swHardwareVersion       DisplayString,
    swSoftwareVersion       DisplayString,
    swCPUMac                MacAddress,
    swType                  DisplayString
}

--xxx.100.6.1.1.1
stackingUnitIndex OBJECT-TYPE
        SYNTAX      INTEGER
        MAX-ACCESS  read-only
        STATUS      current
        DESCRIPTION "This object identifies the switch within the system
                     for which this entry contains information. This
                     value can never be greater than switchNumber."
        ::= { jumblyStackingInfoEntry 1 }

--xxx.100.6.1.1.2
swHardwareVersion OBJECT-TYPE
    SYNTAX  DisplayString (SIZE(1..32))
    MAX-ACCESS  read-only
    STATUS  current
    DESCRIPTION
        " The text string denoting the version of the hardware."
    ::= { jumblyStackingInfoEntry  2 }

--xxx.100.6.1.1.3
swSoftwareVersion OBJECT-TYPE
    SYNTAX  DisplayString (SIZE(1..32))
    MAX-ACCESS  read-only
    STATUS  current
    DESCRIPTION
        " The text string denoting the version of the software."
    ::= { jumblyStackingInfoEntry  3 }

--xxx.100.6.1.1.4
swCPUMac OBJECT-TYPE
    SYNTAX  MacAddress
    MAX-ACCESS  read-only
    STATUS  current
    DESCRIPTION
        " the Mac address of the machine."
    ::= { jumblyStackingInfoEntry  4 } 
    
--xxx.100.6.1.1.5
swType OBJECT-TYPE
    SYNTAX  DisplayString (SIZE(1..32))
    MAX-ACCESS  read-only
    STATUS  current
    DESCRIPTION "Type of this switch."
    ::= { jumblyStackingInfoEntry 5 }

--********************************************************************************************************
--******************************************************************************************************** 
    
--xxx.100.7 uamSecurityPortMib

--xxx.100.7.1
portSecurityTable OBJECT-TYPE
        SYNTAX      SEQUENCE OF PortSecurityEntry
        MAX-ACCESS  not-accessible
        STATUS      current
        DESCRIPTION "The table of port security "
        ::= { priUamSecurityPortMib 1 }

--xxx.100.7.1.1
portSecurityEntry OBJECT-TYPE
        SYNTAX      PortSecurityEntry
        MAX-ACCESS  not-accessible
        STATUS      current
        DESCRIPTION "An entry in the port security table."
        INDEX       { psPortIndex }
        ::= { portSecurityTable 1 }

PortSecurityEntry ::= SEQUENCE
{
    psPortIndex                 INTEGER,
    psPortSecurity              INTEGER,
    psSecuritytSaticMacAdd      MacAddress,
    psSecurityStaticMacDel      MacAddress,
    psSecurityPortLock          INTEGER,
    psSecurityPortMax           INTEGER,
    psSecurityPortConvertmac    INTEGER,
    psSecurityPortLocktimer     INTEGER
}

--xxx.100.7.1.1.1
psPortIndex OBJECT-TYPE
        SYNTAX      INTEGER
        MAX-ACCESS  not-accessible
        STATUS      current
        DESCRIPTION "A unique value for each port"
        ::= { portSecurityEntry 1 }
        
--xxx.100.7.1.1.2
psPortSecurity OBJECT-TYPE
        SYNTAX      INTEGER {
                            disable(0),
                            enable(1)
                           }
        MAX-ACCESS  read-write
        STATUS      current
        DESCRIPTION "enable or disable mac bind on this port"
        ::= { portSecurityEntry 2 } 
        
--xxx.100.7.1.1.3
psSecuritytSaticMacAdd OBJECT-TYPE
        SYNTAX      MacAddress 
        MAX-ACCESS  read-write
        STATUS      current
        DESCRIPTION "bind Security mac address on this port"
        ::= { portSecurityEntry 3 } 
        
--xxx.100.7.1.1.4
psSecurityStaticMacDel OBJECT-TYPE
        SYNTAX      MacAddress 
        MAX-ACCESS  read-write
        STATUS      current
        DESCRIPTION "delete Security mac address on this port"
        ::= { portSecurityEntry 4 }  
                  
--xxx.100.7.1.1.5
psSecurityPortLock OBJECT-TYPE
        SYNTAX      INTEGER{
                            unlock(0),
                            lock(1)
                           }
        MAX-ACCESS  read-write
        STATUS      current
        DESCRIPTION "lock or unlock this port"
        ::= { portSecurityEntry 5 }
        
--xxx.100.7.1.1.6
psSecurityPortMax OBJECT-TYPE
        SYNTAX      INTEGER (1..128)
        MAX-ACCESS  read-write
        STATUS      current
        DESCRIPTION "Maximum secure addrs on this port"
        ::= { portSecurityEntry 6 }
 
--xxx.100.7.1.1.7
psSecurityPortConvertmac OBJECT-TYPE
        SYNTAX      INTEGER (1)
        MAX-ACCESS  read-write
        STATUS      current
        DESCRIPTION "convert dynamic mac to security mac"
        ::= { portSecurityEntry 7 }                                      

--xxx.100.7.1.1.8
psSecurityPortLocktimer OBJECT-TYPE
        SYNTAX      INTEGER (0..300)
        MAX-ACCESS  read-write
        STATUS      current
        DESCRIPTION "lock timer on this port"
        ::= { portSecurityEntry 8 }
        
--xxx.100.7.2
securityMacPortTable OBJECT-TYPE
        SYNTAX      SEQUENCE OF SecurityMacPortEntry
        MAX-ACCESS  not-accessible
        STATUS      current
        DESCRIPTION "Table of descriptive and status information about security port"
        ::= { priUamSecurityPortMib 2 }
        
--xxx.100.7.2.1
securityMacPortEntry OBJECT-TYPE
        SYNTAX      SecurityMacPortEntry
        MAX-ACCESS  not-accessible
        STATUS      current
        DESCRIPTION "An entry in the security mac port table."
        INDEX       { secPortIndex , secMacAdress }
        ::= { securityMacPortTable 1 }

SecurityMacPortEntry ::= SEQUENCE
{
    secPortIndex                 INTEGER,
    secMacAdress                 MacAddress,
    secVid                       INTEGER
}

--xxx.100.7.2.1.1
secPortIndex OBJECT-TYPE
        SYNTAX      INTEGER
        MAX-ACCESS  read-only
        STATUS      current
        DESCRIPTION "A unique value for each port"
        ::= { securityMacPortEntry 1 }   

--xxx.100.7.2.1.2
secMacAdress OBJECT-TYPE
        SYNTAX      MacAddress 
        MAX-ACCESS  read-only
        STATUS      current
        DESCRIPTION "Mac adress bind on this port"
        ::= { securityMacPortEntry 2 }  
        
--xxx.100.7.2.1.3
secVid OBJECT-TYPE
        SYNTAX      INTEGER
        MAX-ACCESS  read-only
        STATUS      current
        DESCRIPTION "vlan id of this port(pvid)"
        ::= { securityMacPortEntry 3 } 
        
--********************************************************************************************************
--******************************************************************************************************** 
         
-- (xxx.100.8)   priIgmpSnoopingMib
    
--xxx.100.8.1
priIgmpSnoopingGlobalEnable OBJECT-TYPE
    SYNTAX  INTEGER
    {
         disable(0),
         enable(1)
    }   
    MAX-ACCESS  read-write
    STATUS  current
    DESCRIPTION
        " Enable or disable the IgmpSnooping algorithm in the switch."
    ::= { priIgmpSnoopingMib  1 }

--xxx.100.8.2
priIgmpSnoopingVlanTable OBJECT-TYPE
    SYNTAX  SEQUENCE OF PriIgmpSnoopingVlanEntry
    MAX-ACCESS  not-accessible
    STATUS  current
    DESCRIPTION
        " IopgmpSnoing configuration in vlan."
    ::= { priIgmpSnoopingMib   2 }

--xxx.100.8.2.1
    priIgmpSnoopingVlanEntry OBJECT-TYPE
        SYNTAX  PriIgmpSnoopingVlanEntry
        MAX-ACCESS  not-accessible
        STATUS  current
        DESCRIPTION
            " IgmpSnooping confition in vlan."
        INDEX   { priIgmpSnoopingvlanID }
        ::= { priIgmpSnoopingVlanTable 1 }

    PriIgmpSnoopingVlanEntry
        ::= SEQUENCE
            {
    		priIgmpSnoopingvlanID                  INTEGER,            
                priIgmpSnoopingvlanEnable              INTEGER,
                priIgmpSnoopingleave                   INTEGER,
                priIgmpSnoopingL2gen                   INTEGER,
                priIgmpSnoopingGroupNum                INTEGER,
                priIgmpSnoopingSourceNum               INTEGER,  
                priIgmpSnoopingPort		            OCTET STRING,
				priIgmpSnoopingNoPort		            OCTET STRING,
                priIgmpSnoopingPortTime		       INTEGER,
                priIgmpSnoopingQueryInterval	       INTEGER,
                priIgmpSnoopingQueryMrsp	       INTEGER,
                priIgmpSnoopingQueryRobustness         INTEGER,
                priIgmpSnoopingSuppression             INTEGER                                              
            }
            
--xxx.100.8.2.1.1
priIgmpSnoopingvlanID OBJECT-TYPE
        SYNTAX      INTEGER
        MAX-ACCESS  not-accessible
        STATUS      current
        DESCRIPTION "This value is vlan's ID."
        ::= { priIgmpSnoopingVlanEntry 1 }
                    
--xxx.100.8.2.1.2
        priIgmpSnoopingvlanEnable OBJECT-TYPE
            SYNTAX      INTEGER
    	    {
         	disable(0),
         	enable(1)
    	    }             
            MAX-ACCESS  read-write
            STATUS      current
            DESCRIPTION " Enable or disable the IgmpSnooping in the switch.Default:0"
            ::= { priIgmpSnoopingVlanEntry 2 } 
            
--xxx.100.8.2.1.3
        priIgmpSnoopingleave OBJECT-TYPE
            SYNTAX      INTEGER
    	    {
         	no-immediate-leave(0),
         	immediate-leave(1)
    	    }             
            MAX-ACCESS  read-write
            STATUS      current
            DESCRIPTION " Enable or disable the immediate leave config.Default:0"
            ::= { priIgmpSnoopingVlanEntry 3 } 
            
--xxx.100.8.2.1.4
        priIgmpSnoopingL2gen OBJECT-TYPE
            SYNTAX      INTEGER
    	    {
         	no-l2-general-querier(0),
         	l2-general-querier(1)
    	    }             
            MAX-ACCESS  read-write
            STATUS      current
            DESCRIPTION " Enable or disable the l2-general-querier config.Default:0"
            ::= { priIgmpSnoopingVlanEntry 4 } 
            
--xxx.100.8.2.1.5
        priIgmpSnoopingGroupNum OBJECT-TYPE
            SYNTAX      INTEGER (1..65535)            
            MAX-ACCESS  read-write
            STATUS      current
            DESCRIPTION "set the maximum IGMP group the port can join"
            ::= { priIgmpSnoopingVlanEntry 5 } 
            
--xxx.100.8.2.1.6
        priIgmpSnoopingSourceNum OBJECT-TYPE
            SYNTAX      INTEGER (1..65535)         
            MAX-ACCESS  read-write
            STATUS      current
            DESCRIPTION "set the maximum source number"
            ::= { priIgmpSnoopingVlanEntry 6 } 

--xxx.100.8.2.1.7
        priIgmpSnoopingPort OBJECT-TYPE
            SYNTAX      OCTET STRING(SIZE(0..255))			
            MAX-ACCESS  read-write
            STATUS      current
            DESCRIPTION " set static mrouter port of vlan.
      		ethernet:  Name of Ethernet port
      		ifname:  Name of interface
      		port-channel: Port aggregation."
            ::= { priIgmpSnoopingVlanEntry 7 } 
--xxx.100.8.2.1.8
        priIgmpSnoopingNoPort OBJECT-TYPE
            SYNTAX      OCTET STRING(SIZE(0..255))			
            MAX-ACCESS  read-write
            STATUS      current
            DESCRIPTION " unset static mrouter port of vlan.
      		ethernet:  Name of Ethernet port
      		ifname:  Name of interface
      		port-channel: Port aggregation."
            ::= { priIgmpSnoopingVlanEntry 8 } 
--xxx.100.8.2.1.9
        priIgmpSnoopingPortTime OBJECT-TYPE
            SYNTAX      INTEGER (1..65535)       
            MAX-ACCESS  read-write
            STATUS      current
            DESCRIPTION " Configure this survive time of mrouter port.Default: 255s"
            ::= { priIgmpSnoopingVlanEntry 9 } 

--xxx.100.8.2.1.10
        priIgmpSnoopingQueryInterval OBJECT-TYPE
            SYNTAX      INTEGER(1..65535)      
            MAX-ACCESS  read-write
            STATUS      current
            DESCRIPTION " Configure this query interval. Default: 125s"
            ::= { priIgmpSnoopingVlanEntry 10 } 
            
--xxx.100.8.2.1.11
        priIgmpSnoopingQueryMrsp OBJECT-TYPE
            SYNTAX      INTEGER(1..25)     
            MAX-ACCESS  read-write
            STATUS      current
            DESCRIPTION " Configure the maximum query response period. Default: 10s"
            ::= { priIgmpSnoopingVlanEntry 11 } 
            
--xxx.100.8.2.1.12
        priIgmpSnoopingQueryRobustness OBJECT-TYPE
            SYNTAX      INTEGER(2..10)        
            MAX-ACCESS  read-write
            STATUS      current
            DESCRIPTION " Configure the query robustness.Default: 2"
            ::= { priIgmpSnoopingVlanEntry 12 }             

--xxx.100.8.2.1.13
        priIgmpSnoopingSuppression OBJECT-TYPE
            SYNTAX      INTEGER(1..65535)        
            MAX-ACCESS  read-write
            STATUS      current
            DESCRIPTION " Configure the suppression query time.Default: 255s"
            ::= { priIgmpSnoopingVlanEntry 13 } 
            
--xxx.100.8.3
priIgmpSnoopingBindTable OBJECT-TYPE
    SYNTAX  SEQUENCE OF PriIgmpSnoopingBindEntry
    MAX-ACCESS  not-accessible
    STATUS  current
    DESCRIPTION
        " IgmpSnoing bind configuration."
    ::= { priIgmpSnoopingMib   3 }
    
--xxx.100.8.3.1
    priIgmpSnoopingBindEntry OBJECT-TYPE
        SYNTAX  PriIgmpSnoopingBindEntry
        MAX-ACCESS  not-accessible
        STATUS  current
        DESCRIPTION
            " IgmpSnooping bind configuration."
        INDEX   { priIgmpSnoopingVlanID, priIgmpSnoopingGroupAddress }
        ::= { priIgmpSnoopingBindTable 1 }

    PriIgmpSnoopingBindEntry
        ::= SEQUENCE
            {
    		        priIgmpSnoopingVlanID                  INTEGER,     
                priIgmpSnoopingGroupAddress               IpAddress,
                priIgmpSnoopingPortBitmap              OCTET STRING                                     
            }

--xxx.100.8.3.1.1
priIgmpSnoopingVlanID OBJECT-TYPE
        SYNTAX      INTEGER
        MAX-ACCESS  not-accessible
        STATUS      current
        DESCRIPTION "This value is vlan's ID."
        ::= { priIgmpSnoopingBindEntry 1 }           
        
--xxx.100.8.3.1.2
priIgmpSnoopingGroupAddress OBJECT-TYPE
        SYNTAX      IpAddress
        MAX-ACCESS  not-accessible
        STATUS      current
        DESCRIPTION "This value is group's ip address."
        ::= { priIgmpSnoopingBindEntry 2 }
        
--xxx.100.8.3.1.3
priIgmpSnoopingPortBitmap OBJECT-TYPE
        SYNTAX      OCTET STRING
        MAX-ACCESS  read-only
        STATUS      current
        DESCRIPTION "Port's bitmap."
        ::= { priIgmpSnoopingBindEntry 3 }
        
--xxx.100.8.4
priIgmpSnoopingLimitPortTable OBJECT-TYPE
    SYNTAX  SEQUENCE OF PriIgmpSnoopingLimitPortEntry
    MAX-ACCESS  not-accessible
    STATUS  current
    DESCRIPTION
        " IopgmpSnoing limits configuration per port in vlan."
    ::= { priIgmpSnoopingMib   4 }

--xxx.100.8.4.1
    priIgmpSnoopingLimitPortEntry OBJECT-TYPE
        SYNTAX  PriIgmpSnoopingLimitPortEntry
        MAX-ACCESS  not-accessible
        STATUS  current
        DESCRIPTION
            " IgmpSnooping limits confition per port in vlan."
        INDEX   { priIgmpSnoopingLimitVlanID, priIgmpSnoopingLimitPortIndex}
        ::= { priIgmpSnoopingLimitPortTable 1 }

    PriIgmpSnoopingLimitPortEntry
        ::= SEQUENCE
            {
    						priIgmpSnoopingLimitVlanID             INTEGER,            
                priIgmpSnoopingLimitPortIndex          INTEGER,
                priIgmpSnoopingLimitPortGroupNum       INTEGER,
                priIgmpSnoopingLimitPortSourceNum      INTEGER, 
                priIgmpSnoopingLimitPortStrategy       INTEGER, 
                priIgmpSnoopingLimitPortStatus         INTEGER                                              
            }
            
--xxx.100.8.4.1.1
priIgmpSnoopingLimitVlanID OBJECT-TYPE
        SYNTAX      INTEGER
        MAX-ACCESS  not-accessible
        STATUS      current
        DESCRIPTION "This value is vlan's ID which enable ip igmp snooping."
        ::= { priIgmpSnoopingLimitPortEntry 1 }
--xxx.100.8.4.1.2       
 priIgmpSnoopingLimitPortIndex OBJECT-TYPE
        SYNTAX      INTEGER
        MAX-ACCESS  not-accessible
        STATUS      current
        DESCRIPTION "This value is port's Index."
        ::= { priIgmpSnoopingLimitPortEntry 2 }  
--xxx.100.8.4.1.3  
priIgmpSnoopingLimitPortGroupNum OBJECT-TYPE
		    SYNTAX      INTEGER (1..65535)            
		    MAX-ACCESS  read-write
		    STATUS      current
		    DESCRIPTION "set the maximum IGMP group the port can join.Default:FFFFFFFF, if only set source_num,
		    when geting ,the result is -1(FFFFFFFF)"
		    ::= { priIgmpSnoopingLimitPortEntry 3 } 
            
--xxx.100.8.4.1.4 
priIgmpSnoopingLimitPortSourceNum OBJECT-TYPE
		    SYNTAX      INTEGER (1..65535)         
		    MAX-ACCESS  read-write
		    STATUS      current
		    DESCRIPTION "set the maximum source number the port can join.Default:FFFFFFFF, if only set group_num,
		    when geting ,the result is -1(FFFFFFFF)"
		    ::= { priIgmpSnoopingLimitPortEntry 4 }   	                         
--xxx.100.8.4.1.5  
priIgmpSnoopingLimitPortStrategy OBJECT-TYPE
				SYNTAX  INTEGER
  	    {
  	    	replace(1),
     		  drop(2)
  	    }
  			MAX-ACCESS  read-write
  			STATUS      current
  			DESCRIPTION "configure the strategy over limit."
  			::= {priIgmpSnoopingLimitPortEntry 5}     
--xxx.100.8.4.1.6
priIgmpSnoopingLimitPortStatus OBJECT-TYPE
    		SYNTAX  INTEGER
    		{
        	enable(1),  
			disable(0)    		
    		}
    		MAX-ACCESS  read-write
    		STATUS      current
    		DESCRIPTION "the status of limitPort:enable(1) to enable value of limitation;
        disable(0) is to disable value of limitation."
     		::= {priIgmpSnoopingLimitPortEntry 6 }

--xxx.100.8.5
priIgmpSnoopingPortCtrlPktTable OBJECT-TYPE
		SYNTAX  SEQUENCE OF PriIgmpSnoopingPortCtrlPktEntry
		MAX-ACCESS  not-accessible
		STATUS  current
		DESCRIPTION
			" IgmpSnooping filter of the layer 3 control packet function of a port."
		::= { priIgmpSnoopingMib   5 }

--xxx.100.8.5.1
	priIgmpSnoopingPortCtrlPktEntry OBJECT-TYPE
			SYNTAX  PriIgmpSnoopingPortCtrlPktEntry
			MAX-ACCESS  not-accessible
			STATUS  current
			DESCRIPTION
				" IgmpSnooping control packet per port."
			INDEX   { priIgmpSnoopingPortCtrlPktDrop}
			::= { priIgmpSnoopingPortCtrlPktTable 1 }

	PriIgmpSnoopingPortCtrlPktEntry
			::= SEQUENCE
		{
			priIgmpSnoopingPortCtrlPktDrop             INTEGER                                          
		}
--xxx.100.8.5.1.1
priIgmpSnoopingPortCtrlPktDrop OBJECT-TYPE
        SYNTAX      INTEGER
		{
			query(1),
			report(2),
			query-and-report(3),
			no-query(4),
			no-report(5)
		}
        MAX-ACCESS  read-write
        STATUS      current
        DESCRIPTION " if set(1), drop query packet ,
						 and if set(2), drop report packet,
						 if set(4), no drop query packet ,
						 and if set(5), no drop report packet,
						 query_and_report(3): drop query and report packet,"
        ::= { priIgmpSnoopingPortCtrlPktEntry 1 }	
		
--xxx.100.8.6
priIgmpSnoopingPortAuthTable OBJECT-TYPE
    SYNTAX  SEQUENCE OF PriIgmpSnoopingPortAuthEntry
    MAX-ACCESS  not-accessible
    STATUS  current
    DESCRIPTION
        " This table is used to manage the IGMP Access Authentication 
            configurations of a port."
    ::= { priIgmpSnoopingMib   6 }

--xxx.100.8.6.1
    priIgmpSnoopingPortAuthEntry OBJECT-TYPE
        SYNTAX  PriIgmpSnoopingPortAuthEntry
        MAX-ACCESS  not-accessible
        STATUS  current
        DESCRIPTION
            " IgmpSnooping: A list of manageable entities for IGMP Access Authentication.
            The configuration is done per port."
        INDEX   { priIgmpSnoopingPortAuthEnable}
        ::= { priIgmpSnoopingPortAuthTable 1 }

    PriIgmpSnoopingPortAuthEntry
        ::= SEQUENCE
            {
    			priIgmpSnoopingPortAuthEnable             INTEGER,
				priIgmpSnoopingPortAuthFreeRule           OCTET STRING
            }

--xxx.100.8.6.1.1
priIgmpSnoopingPortAuthEnable OBJECT-TYPE
        SYNTAX      INTEGER
		{
		            disable(0),
					enable(1)
		}
        MAX-ACCESS  read-write
        STATUS      current
        DESCRIPTION "If set(0), not enable igmp snooping authentication on port, 
						 if set(1), enable igmp snooping authentication on port."
        ::= { priIgmpSnoopingPortAuthEntry 1 }
--xxx.100.8.6.1.2
priIgmpSnoopingPortAuthFreeRule OBJECT-TYPE
        SYNTAX      OCTET STRING(SIZE(0..255))
        MAX-ACCESS  read-only
        STATUS      current
        DESCRIPTION "get the igmpsnooping authentication group control"
        ::= { priIgmpSnoopingPortAuthEntry 2 }		
--********************************************************************************************************		                                                                                                
--********************************************************************************************************
        
-- (xxx.100.9)   QinQ group

--xxx.100.9.1
dot1qTunnelTable OBJECT-TYPE
    SYNTAX  SEQUENCE OF Dot1qTunnelEntry
    MAX-ACCESS  not-accessible
    STATUS  current
    DESCRIPTION
    	" port of qinq tunnel function list"
    ::= { priQinQmib  1}   

--xxx.100.9.1
dot1qTunnelEntry OBJECT-TYPE
        SYNTAX  Dot1qTunnelEntry
        MAX-ACCESS  not-accessible
        STATUS  current
        DESCRIPTION
            " configure of dot1qTunnel"
        INDEX   { qinqPortIndex }
        ::= { dot1qTunnelTable 1 }
        
Dot1qTunnelEntry
        ::= SEQUENCE
            {
            	qinqPortIndex			INTEGER,
            	tunnelPortEnable		INTEGER,
                tunnelPortType			INTEGER
            }

--xxx.100.9.1.1
qinqPortIndex OBJECT-TYPE
    SYNTAX  INTEGER
            MAX-ACCESS  not-accessible
            STATUS  current
            DESCRIPTION
                "port index"
            ::= { dot1qTunnelEntry 1 } 
            
--xxx.100.9.1.2
tunnelPortEnable OBJECT-TYPE
    SYNTAX  INTEGER {
                disable(0),
                enable(1)
            }
            MAX-ACCESS  read-write
            STATUS  current
            DESCRIPTION
                "Enable or disable the dot1q-tunnel in this port."
            ::= { dot1qTunnelEntry 2 }  
            
--xxx.100.9.1.3
tunnelPortType OBJECT-TYPE
    SYNTAX  INTEGER 
            MAX-ACCESS  read-write
            STATUS  current
            DESCRIPTION
                "Protocol type of trunk port(TPID)(exp:33024(0x8100)/37120(0x9100)/37376(0x9200))."
            ::= { dot1qTunnelEntry 3 }   


            
--xxx.100.9.2
vlanTranslationTable OBJECT-TYPE
    SYNTAX  SEQUENCE OF VlanTranslationEntry
    MAX-ACCESS  not-accessible
    STATUS  current
    DESCRIPTION
    	" VLAN translation basic config."
    ::= { priQinQmib  2}   

--xxx.100.9.2.1
vlanTranslationEntry OBJECT-TYPE
        SYNTAX  VlanTranslationEntry
        MAX-ACCESS  not-accessible
        STATUS  current
        DESCRIPTION
            "VLAN translation"
        INDEX   { translatPortIndex }
        ::= { vlanTranslationTable 1 }
        
VlanTranslationEntry
        ::= SEQUENCE
            {
            	translatPortIndex	      INTEGER,
    		translationEnable             INTEGER,
    		translationDropType           INTEGER		
            }
 
--xxx.100.9.2.1.1
translatPortIndex OBJECT-TYPE
    SYNTAX  INTEGER 
            MAX-ACCESS  not-accessible
            STATUS  current
            DESCRIPTION
                "Index of Port."
            ::= { vlanTranslationEntry 1 }
            
--xxx.100.9.2.1.2
translationEnable OBJECT-TYPE
    SYNTAX  INTEGER {
                disable(0),
                enable(1)
            }
            MAX-ACCESS  read-write
            STATUS  current
            DESCRIPTION
                "if the port can be done translation function"
            ::= { vlanTranslationEntry 2 }  
            
--xxx.100.9.2.1.3
translationDropType OBJECT-TYPE
    SYNTAX  INTEGER {
		in(1),
		out(2),
		both(3),
		noIn(4),
		noOut(5),
		noBoth(6)
            }
            MAX-ACCESS  read-write
            STATUS  current
            DESCRIPTION
                "when VLAN-translation missed, drop packet mode"
            ::= { vlanTranslationEntry 3 } 


--xxx.100.9.3
vlanTranslationTypeTable OBJECT-TYPE
    SYNTAX  SEQUENCE OF VlanTranslationTypeEntry
    MAX-ACCESS  not-accessible
    STATUS  current
    DESCRIPTION
    	" port VLAN-translation of translation relation list"
    ::= { priQinQmib  3}   

--xxx.100.9.3.1
vlanTranslationTypeEntry OBJECT-TYPE
        SYNTAX  VlanTranslationTypeEntry
        MAX-ACCESS  not-accessible
        STATUS  current
        DESCRIPTION
            " port VLAN translation of translation relation,index is port index and translation sort"
        INDEX   { translatPortTypeIndex , translationType ,translationOldVlanid ,translationNewVlanid}
        ::= { vlanTranslationTypeTable 1 }
        
VlanTranslationTypeEntry
        ::= SEQUENCE
            {
            	translatPortTypeIndex	      INTEGER,
    		translationType               INTEGER, 
    		translationOldVlanid   	      INTEGER,
    		translationNewVlanid   	      INTEGER,
    		translationTypeStatus	      INTEGER			
            }
 
--xxx.100.9.3.1.1
translatPortTypeIndex OBJECT-TYPE
    SYNTAX  INTEGER 
            MAX-ACCESS  read-only
            STATUS  current
            DESCRIPTION
                "port index"
            ::= { vlanTranslationTypeEntry 1 }

        
--xxx.100.9.3.1.2
translationType OBJECT-TYPE
    SYNTAX  INTEGER{
		in(1),
		out(2)    
    		}
            MAX-ACCESS  read-only
            STATUS  current
            DESCRIPTION
                "translation type. in:input translation; out:output translation."
            ::= { vlanTranslationTypeEntry 2 } 

--xxx.100.9.3.1.3
translationOldVlanid OBJECT-TYPE
    SYNTAX  INTEGER (1..4094)
            MAX-ACCESS  read-only
            STATUS  current
            DESCRIPTION
                "vlantranslation pre-vid"
            ::= { vlanTranslationTypeEntry 3 } 
            
--xxx.100.9.3.1.4
translationNewVlanid OBJECT-TYPE
    SYNTAX  INTEGER (1..4094)
            MAX-ACCESS  read-only
            STATUS  current
            DESCRIPTION
                "the new vid"
            ::= { vlanTranslationTypeEntry 4 } 

--xxx.100.9.3.1.5
        translationTypeStatus OBJECT-TYPE
            SYNTAX  INTEGER
            	    {            	    	
               		active(1),
               		destroy(2)
            	    }
            MAX-ACCESS  read-create
            STATUS  current
            DESCRIPTION
                " accession/delete VLAN-translation relation"
            ::= { vlanTranslationTypeEntry  5 }    

                                       
--********************************************************************************************************
--********************************************************************************************************              

-- (xxx.100.10)   prisecurity group

--xxx.100.10.1
    acl         	    OBJECT IDENTIFIER ::= { prisecurity 1 } 
--xxx.100.10.1.1
    fireWall         	    OBJECT IDENTIFIER ::= { acl 1 } 
--xxx.100.10.1.2
    timeRange         	    OBJECT IDENTIFIER ::= { acl 2 }     
--xxx.100.10.1.3
   aclConfig         	    OBJECT IDENTIFIER ::= { acl 3 }    
--xxx.100.10.1.4
   aclAttach        	    OBJECT IDENTIFIER ::= { acl 4 }
    

--xxx.100.10.1.1.1
fireWallEnable OBJECT-TYPE
    SYNTAX  INTEGER{
                disable(0),
                enable(1)
            }
            MAX-ACCESS  read-write
            STATUS  current
            DESCRIPTION
                "firewall on-off"
            ::= { fireWall 1 } 
            

--******************************************************************************************************** 

--xxx.100.10.1.2.1
timeRangeMapTable OBJECT-TYPE
    SYNTAX  SEQUENCE OF TimeRangeMapEntry
    MAX-ACCESS  not-accessible
    STATUS  current
            DESCRIPTION
                "timeRange Map Table"
            ::= { timeRange 1 } 
            
--xxx.100.10.1.2.1.1
    timeRangeMapEntry OBJECT-TYPE
        SYNTAX  TimeRangeMapEntry
        MAX-ACCESS  not-accessible
        STATUS  current
        DESCRIPTION
            "timeRange Map Entry"
        INDEX   { timeRangeMapIndex }
        ::= { timeRangeMapTable 1 }

    TimeRangeMapEntry
        ::= SEQUENCE
            {
               timeRangeMapIndex        INTEGER,
               timeRangeMapName		   DisplayString,
               timeRangeMapStatus		    INTEGER         
            }
            
--xxx.100.10.1.2.1.1.1
        timeRangeMapIndex OBJECT-TYPE
            SYNTAX  INTEGER
            MAX-ACCESS  read-only
            STATUS  current
            DESCRIPTION
                "TimeRange Map index,the range of it is 1-(2^32-1)."
            ::= { timeRangeMapEntry 1 }
            
--xxx.100.10.1.2.1.1.2
        timeRangeMapName OBJECT-TYPE
            SYNTAX  DisplayString(SIZE (1..64))
            MAX-ACCESS  read-write
            STATUS  current
            DESCRIPTION
                "TimeRange Map name"
            ::= { timeRangeMapEntry 2 }

--xxx.100.10.1.2.1.1.3
        timeRangeMapStatus OBJECT-TYPE
             SYNTAX  INTEGER
            	    {   
            	       createAndGo(0),         	    	
               		   active(1),
               		   destroy(2)
            	    }
            MAX-ACCESS  read-write
            STATUS  current
            DESCRIPTION
                "TimeRange Map status"
            ::= { timeRangeMapEntry 3 }
                                                                       
--xxx.100.10.1.2.2
timeRangeTable OBJECT-TYPE
    SYNTAX  SEQUENCE OF TimeRangeEntry
    MAX-ACCESS  not-accessible
    STATUS  current
            DESCRIPTION
                "timeRange Table"
            ::= { timeRange 2 } 
                
--xxx.100.10.1.2.2.1
    timeRangeEntry OBJECT-TYPE
        SYNTAX  TimeRangeEntry
        MAX-ACCESS  not-accessible
        STATUS  current
        DESCRIPTION
            "timeRange Entry"
        INDEX   { timeRangeIndex,timeRangeSubIndex }
        ::= { timeRangeTable 1 }

    TimeRangeEntry
        ::= SEQUENCE
            {
                timeRangeIndex        INTEGER,
                timeRangeSubIndex     INTEGER,
                timeRangeType		      INTEGER,
                timeRangeStartWeek		    BITS,
                timeRangeStartDate		    DisplayString,
                timeRangeStartTime		    DisplayString,  
                timeRangeEndWeek	    BITS,
                timeRangeEndDate	    DisplayString,
                timeRangeEndTime	    DisplayString,             
                timeRangeStatus       INTEGER
            }

--xxx.100.10.1.2.2.1.1
        timeRangeIndex OBJECT-TYPE
            SYNTAX  INTEGER
            MAX-ACCESS  read-only
            STATUS  current
            DESCRIPTION
                "TimeRange index,the allowed range is 1 to 1000."
            ::= { timeRangeEntry 1 }

--xxx.100.10.1.2.2.1.2
        timeRangeSubIndex OBJECT-TYPE
            SYNTAX  INTEGER
            MAX-ACCESS  read-only
            STATUS  current
            DESCRIPTION
                "TimeRange sub index,the allowed range is 1 to 1000."
            ::= { timeRangeEntry 2}
                                  
--xxx.100.10.1.2.2.1.3
        timeRangeType OBJECT-TYPE
            SYNTAX  INTEGER 
            {
                absolute(1),
                periodic(2)
            }
            MAX-ACCESS  read-write
            STATUS  current
            DESCRIPTION
                "TimeRange type"
            ::= { timeRangeEntry 3 }

--xxx.100.10.1.2.2.1.4
        timeRangeStartWeek OBJECT-TYPE
            SYNTAX  BITS 
                    {
            	    	monday(0),
               		  tuesday(1),
               		  wednesday(2),
            	    	thursday(3),
               		  friday(4),
               		  saturday(5),
               		  sunday(6)               		            	
            	    }
            MAX-ACCESS  read-write
            STATUS  current
            DESCRIPTION
                "configurate the start week,for example: f8 means monday+tuesday+wednesday+thurday+friday,
                the lowest bit is not used,so fe is the biggest."
            ::= { timeRangeEntry 4 }

--xxx.100.10.1.2.2.1.5
        timeRangeStartDate OBJECT-TYPE
            SYNTAX  DisplayString 
            MAX-ACCESS  read-write
            STATUS  current
            DESCRIPTION
                "configurate the start Date,for example YYYY.MM.DD ."
            ::= { timeRangeEntry 5 }  
                        
--xxx.100.10.1.2.2.1.6
        timeRangeStartTime OBJECT-TYPE
            SYNTAX  DisplayString 
            MAX-ACCESS  read-write
            STATUS  current
            DESCRIPTION
                "configurate the start clock,for example HH:MM:SS."
            ::= { timeRangeEntry 6}
            
          
            
--xxx.100.10.1.2.2.1.7
        timeRangeEndWeek OBJECT-TYPE
            SYNTAX  BITS 
                    {
            	    	monday(0),
               		  tuesday(1),
               		  wednesday(2),
            	    	thursday(3),
               		  friday(4),
               		  saturday(5),
               		  sunday(6)               		            	
            	    }
            MAX-ACCESS  read-write
            STATUS  current
            DESCRIPTION
                "configurate the end week,for example: f8 means monday+tuesday+wednesday+thurday+friday,
                the lowest bit is not used,so fe is the biggest."
            ::= { timeRangeEntry 7 }
            
--xxx.100.10.1.2.2.1.8
        timeRangeEndDate OBJECT-TYPE
            SYNTAX  DisplayString 
            MAX-ACCESS  read-write
            STATUS  current
            DESCRIPTION
                "configurate the end date,for example YYYY.MM.DD."
            ::= { timeRangeEntry 8 }  
                        
--xxx.100.10.1.2.2.1.9
        timeRangeEndTime OBJECT-TYPE
            SYNTAX  DisplayString 
            MAX-ACCESS  read-write
            STATUS  current
            DESCRIPTION
                "configurate the end clock,for example HH:MM:SS."
            ::= { timeRangeEntry 9 }
            

            
--xxx.100.10.1.2.2.1.10
        timeRangeStatus OBJECT-TYPE
            SYNTAX  INTEGER
            	    {    
            	     createAndGo(0),       	    	
               		  active(1),
               		  destroy(2)
            	    }
            MAX-ACCESS  read-write
            STATUS  current
            DESCRIPTION
                "status of timeRangeMapTable"
            ::= { timeRangeEntry  10 }    
               
  
--********************************************************************************************************

--xxx.100.10.1.3.1
numAclGroupTable OBJECT-TYPE
    SYNTAX  SEQUENCE OF NumAclGroupEntry
    MAX-ACCESS  not-accessible
    STATUS  current
            DESCRIPTION
                "this table is used for building a num-acl list."
            ::= { aclConfig 1  } 
            
--xxx.100.10.1.3.1.1
   numAclGroupEntry OBJECT-TYPE
        SYNTAX  NumAclGroupEntry
        MAX-ACCESS  not-accessible
        STATUS  current
        DESCRIPTION
            "numAclGroup Table's Entry"
        INDEX   { numAclGroupAclIndex }
        ::= { numAclGroupTable 1 }

    NumAclGroupEntry
        ::= SEQUENCE
            {
               numAclGroupAclIndex        INTEGER,
               numAclGroupMatchOrder		   INTEGER,
               numAclGroupSubitemNum		    INTEGER,
               numAclGroupStatus           INTEGER
            }
--xxx.100.10.1.3.1.1.1
        numAclGroupAclIndex OBJECT-TYPE
            SYNTAX  INTEGER 
            MAX-ACCESS read-only
            STATUS  current
            DESCRIPTION
                "the index of number acl,ip standard <1-99>,ip extern <100-199>, 
                ip extern (support discontinuous ip address mask)<200-299>, mac standard <700-799>,
                mac extern <1100-1199>,ipv6 standard <500-599> ipv6 extern <600-699>,
                mac-ip extern <3100-3199>,mac-ip extern(support discontinuous ip address mask) <3200-3299>"
            ::= { numAclGroupEntry 1 }

--xxx.100.10.1.3.1.1.2
        numAclGroupMatchOrder OBJECT-TYPE
            SYNTAX  INTEGER
                  {
                    autoPriority(0),
                    configPriority(1)
                  } 
            MAX-ACCESS read-write
            STATUS  current
            DESCRIPTION
                 "value 0 means Acl rule's priority is automatically configured,
                  value 1 means Acl rule's priority is manually configured,
                  but now it's not supported."
            ::= { numAclGroupEntry 2 }
 
 --xxx.100.10.1.3.1.1.3
        numAclGroupSubitemNum OBJECT-TYPE
            SYNTAX  INTEGER 
            MAX-ACCESS read-only
            STATUS  current
            DESCRIPTION
                 "the Number of one acl's rule."
            ::= { numAclGroupEntry 3 }
 
 --xxx.100.10.1.3.1.1.4
       numAclGroupStatus OBJECT-TYPE
            SYNTAX  INTEGER 
                  {
                     createAndGo(0),
                     active(1),
                     destroy(2)
                  }
            MAX-ACCESS read-write
            STATUS  current
            DESCRIPTION
                "the status of number acl."
            ::= { numAclGroupEntry 4 }
            
--***********************************************************************************************************************
--xxx.100.10.1.3.2
nameAclGroupTable OBJECT-TYPE
    SYNTAX  SEQUENCE OF NameAclGroupEntry
    MAX-ACCESS  not-accessible
    STATUS  current
            DESCRIPTION
                "this table is used for building a name-acl list and mapping a string of named acl to a value of number,
                when you want to config name-acl list,you must map at here."
            ::= { aclConfig 2  } 
            
--xxx.100.10.1.3.2.1
    nameAclGroupEntry OBJECT-TYPE
        SYNTAX  NameAclGroupEntry
        MAX-ACCESS  not-accessible
        STATUS  current
        DESCRIPTION
            "nameAclGroup Table's Entry"
        INDEX   { nameAclGroupAclIndex }
        ::= { nameAclGroupTable 1 }

   NameAclGroupEntry
        ::= SEQUENCE
            {
               nameAclGroupAclIndex        INTEGER,
               nameAclGroupAclName         DisplayString,
               nameAclGroupAclType         INTEGER,
               nameAclGroupMatchOrder		   INTEGER,
               nameAclGroupSubitemNum		    INTEGER,
               nameAclGroupStatus           INTEGER
            }
--xxx.100.10.1.3.2.1.1
        nameAclGroupAclIndex OBJECT-TYPE
            SYNTAX  INTEGER 
            MAX-ACCESS read-only
            STATUS  current
            DESCRIPTION
                "the index of name acl,the range starts at 20000."
            ::= { nameAclGroupEntry 1 }

--xxx.100.10.1.3.2.1.2
       nameAclGroupAclName OBJECT-TYPE
            SYNTAX  DisplayString(SIZE (1..64))
            MAX-ACCESS read-write
            STATUS  current
            DESCRIPTION
                "the name of name-acl."
            ::= { nameAclGroupEntry 2 }

--xxx.100.10.1.3.2.1.3
        nameAclGroupAclType OBJECT-TYPE
            SYNTAX  INTEGER
                {
                   ipStandard(0),
                   ipExtern(1),
                   macStandard(2),
                   macExtern(3),
                   macIpExtern(4),
                   macIpStandard(5),
                   ipv6Standard(6),
                   ipv6Extern(7)                 
                } 
            MAX-ACCESS read-write
            STATUS  current
            DESCRIPTION
                "the type of name acl."
            ::= { nameAclGroupEntry 3 } 
                       
--xxx.100.10.1.3.2.1.4
       nameAclGroupMatchOrder OBJECT-TYPE
            SYNTAX  INTEGER
                  {
                    autoPriority(0),
                    configPriority(1)
                  } 
            MAX-ACCESS read-write
            STATUS  current
            DESCRIPTION
                 "value 0 means Acl rule's priority is automatically configured,
                  value 1 means Acl rule's priority is manually configured,
                  but now it's not supported."
            ::= { nameAclGroupEntry 4 }
 
 --xxx.100.10.1.3.2.1.5
        nameAclGroupSubitemNum OBJECT-TYPE
            SYNTAX  INTEGER 
            MAX-ACCESS read-only
            STATUS  current
            DESCRIPTION
                "the Number of one acl's rule."
            ::= { nameAclGroupEntry 5 }
 
 --xxx.100.10.1.3.2.1.6
     nameAclGroupStatus OBJECT-TYPE
            SYNTAX  INTEGER 
                  {
                     createAndGo(0),
                     active(1),
                     destroy(2)
                  }
            MAX-ACCESS read-write
            STATUS  current
            DESCRIPTION
                "the status of nameAclGroupTable."
            ::= { nameAclGroupEntry 6 }
--***************************************************************************************************************
--xxx.100.10.1.3.3
ipStandardAclTable OBJECT-TYPE
    SYNTAX  SEQUENCE OF IpStandardAclEntry
    MAX-ACCESS  not-accessible
    STATUS  current
            DESCRIPTION
                "config ip Standard Acl "
            ::= { aclConfig 3  } 
            
--xxx.100.10.1.3.3.1
    ipStandardAclEntry OBJECT-TYPE
        SYNTAX  IpStandardAclEntry
        MAX-ACCESS  not-accessible
        STATUS  current
        DESCRIPTION
            "ip standard  Table's Entry"
        INDEX   { ipStandardIndex, ipStandardSubIndex}
        ::= { ipStandardAclTable 1 }

    IpStandardAclEntry
        ::= SEQUENCE
            {
               ipStandardIndex        INTEGER,
               ipStandardSubIndex     INTEGER,
               ipStandardPriority     INTEGER,
               ipStandardAct		      INTEGER,
               ipStandardSrcIp		    IpAddress,
               ipStandardSrcIpWild    IpAddress,
               ipStandardStatus       INTEGER
            }
                                                           
--xxx.100.10.1.3.3.1.1
        ipStandardIndex OBJECT-TYPE
            SYNTAX  INTEGER 
            MAX-ACCESS read-only
            STATUS  current
            DESCRIPTION
                "The index of ip-standard-acl group."
            ::= { ipStandardAclEntry 1 }
            
--xxx.100.10.1.3.3.1.2
        ipStandardSubIndex OBJECT-TYPE
            SYNTAX  INTEGER 
            MAX-ACCESS read-only
            STATUS  current
            DESCRIPTION
                "The index of ip-standard-acl rule."
            ::= { ipStandardAclEntry 2 }

--xxx.100.10.1.3.3.1.3
        ipStandardPriority OBJECT-TYPE
            SYNTAX  INTEGER 
            MAX-ACCESS read-write
            STATUS  current
            DESCRIPTION
                "The priority of standard ip acl's rule,it is not supported now."
            ::= { ipStandardAclEntry 3 }
            
                        
--xxx.100.10.1.3.3.1.4
        ipStandardAct OBJECT-TYPE
            SYNTAX  INTEGER 
             	    {
            	    	deny(0),
               		  permit(1)
            	    }            
            MAX-ACCESS  read-write
            STATUS  current
            DESCRIPTION
                " The action of acl rule."
            ::= { ipStandardAclEntry 4 }

            
--xxx.100.10.1.3.3.1.5
        ipStandardSrcIp OBJECT-TYPE
            SYNTAX  IpAddress            
            MAX-ACCESS  read-write
            STATUS  current
            DESCRIPTION
                " Source IP-address of basic acl rule."
            ::= { ipStandardAclEntry 5 }
            
--xxx.100.10.1.3.3.1.6
        ipStandardSrcIpWild OBJECT-TYPE
            SYNTAX  IpAddress           
            MAX-ACCESS  read-write
            STATUS  current
            DESCRIPTION
                " Source IP-address wild  of basic acl rule."
            ::= { ipStandardAclEntry 6 }

--xxx.100.10.1.3.3.1.7
        ipStandardStatus OBJECT-TYPE
            SYNTAX  INTEGER
            	    {
            	    	createAndGo(0),
               		  active(1),
               		  destroy(2)
            	    }
            MAX-ACCESS  read-write
            STATUS  current
            DESCRIPTION
                " status of the ipStandardAclTable."
            ::= { ipStandardAclEntry 7 } 

--********************************************************************************************************
            
--xxx.100.10.1.3.4
ipExternAclTable OBJECT-TYPE
    SYNTAX  SEQUENCE OF IpExternAclEntry
    MAX-ACCESS  not-accessible
    STATUS  current
            DESCRIPTION
                "ip extern Acl Table"
            ::= { aclConfig 4  } 
            
--xxx.100.10.1.3.4.1
    ipExternAclEntry OBJECT-TYPE
        SYNTAX  IpExternAclEntry
        MAX-ACCESS  not-accessible
        STATUS  current
        DESCRIPTION
            "ip extern Table's Entry"
        INDEX   { ipExternIndex,ipExternSubIndex }
        ::= { ipExternAclTable 1 }

    IpExternAclEntry
        ::= SEQUENCE
            {
               ipExternIndex        INTEGER,
               ipExternSubIndex     INTEGER,
               ipExternPriority     INTEGER,               
               ipExternAct		      INTEGER,
               ipExternProtocal     Integer32,
               ipExternSrcIp		    IpAddress,
               ipExternSrcIpWild    IpAddress,
               ipExternDstIp        IpAddress,
               ipExternDstIpWild    IpAddress,
               ipExternTimeRangeName  DisplayString,
               ipExternSrcOp        INTEGER,
               ipExternSrcPort1     INTEGER,
               ipExternSrcPort2     INTEGER,
               ipExternDstOp        INTEGER,
               ipExternDstPort1     INTEGER,
               ipExternDstPort2     INTEGER,
               ipExternStatus         INTEGER
            }
            
--xxx.100.10.1.3.4.1.1
        ipExternIndex OBJECT-TYPE
            SYNTAX  INTEGER 
            MAX-ACCESS read-only
            STATUS  current
            DESCRIPTION
                "The index of ip-Extern-acl group ."
            ::= { ipExternAclEntry 1 }
            
--xxx.100.10.1.3.4.1.2
        ipExternSubIndex OBJECT-TYPE
            SYNTAX  INTEGER 
            MAX-ACCESS read-only
            STATUS  current
            DESCRIPTION
                "The index of ip-Extern-acl rule ."
            ::= { ipExternAclEntry 2 }
            
--xxx.100.10.1.3.4.1.3
        ipExternPriority OBJECT-TYPE
            SYNTAX  INTEGER 
            MAX-ACCESS read-write
            STATUS  current
            DESCRIPTION
              "The priority of extern ip acl's rule,it is not supported now."
            ::= { ipExternAclEntry 3 } 
                       
--xxx.100.10.1.3.4.1.4
        ipExternAct OBJECT-TYPE
            SYNTAX  INTEGER 
             	    {
            	    	deny(0),
               		permit(1)
            	    }            
            MAX-ACCESS  read-write
            STATUS  current
            DESCRIPTION
                " The action of acl rule."
            ::= { ipExternAclEntry 4 }

--xxx.100.10.1.3.4.1.5
        ipExternProtocal OBJECT-TYPE
            SYNTAX Integer32(0..255|65535)           
            MAX-ACCESS  read-write
            STATUS  current
            DESCRIPTION
                "The protocol number field in the IP header used to indicate
        the higher layer protocol as specified in RFC 1700. A value 
        value of 65535 matches every IP packet. 
        
        For example :
        1 is ICMP, 2 is IGMP, 4 is IP in IP encapsulation,
        6 is TCP, 9 is IGRP, 17 is UDP, 47 is GRE, 50 is ESP, 51 is AH,
        88 is EIGRP, 89 is OSPF, 94 is KA9Q/NOS compatible IP over IP,
        103 is PIMv2, 108 is PCP, 65535 is ip."
            ::= { ipExternAclEntry 5}
            
--xxx.100.10.1.3.4.1.6
        ipExternSrcIp OBJECT-TYPE
            SYNTAX  IpAddress            
            MAX-ACCESS  read-write
            STATUS  current
            DESCRIPTION
                " Source IP-address of advanced acl rule,for example 10.1.1.0 ."
            ::= { ipExternAclEntry 6}
            
--xxx.100.10.1.3.4.1.7
        ipExternSrcIpWild OBJECT-TYPE
            SYNTAX  IpAddress           
            MAX-ACCESS  read-write
            STATUS  current
            DESCRIPTION
                " Source IP-address wild  of advanced acl rule,for example 0.0.0.255 ."
            ::= { ipExternAclEntry 7 }

            
--xxx.100.10.1.3.4.1.8
        ipExternDstIp OBJECT-TYPE
            SYNTAX  IpAddress            
            MAX-ACCESS  read-write
            STATUS  current
            DESCRIPTION
                " Destination IP-address of advanced acl rule,for example 10.1.1.0 ."
            ::= { ipExternAclEntry 8 }
            
--xxx.100.10.1.3.4.1.9
        ipExternDstIpWild OBJECT-TYPE
            SYNTAX  IpAddress           
            MAX-ACCESS  read-write
            STATUS  current
            DESCRIPTION
                " Destination IP-address wild  of advanced acl rule,for example 0.0.0.255 ."
            ::= { ipExternAclEntry 9 }


--xxx.100.10.1.3.4.1.10
         ipExternTimeRangeName OBJECT-TYPE
            SYNTAX DisplayString(SIZE (1..64))    
            MAX-ACCESS  read-write
            STATUS  current
            DESCRIPTION
                "The Time-range of advanced acl rule."
            ::= { ipExternAclEntry 10 }
            
--xxx.100.10.1.3.4.1.11
        ipExternSrcOp OBJECT-TYPE
            SYNTAX INTEGER{
                noOperator(0),
			        	eq(1),
			        	range(2)
        	}           
            MAX-ACCESS  read-write
            STATUS  current
            DESCRIPTION
                "Indicates how a packet's source TCP/UDP port number is
        to be compared.
        
        If the numIpExternProtocol object in the same row does not
        indicate TCP or UDP, this object has to be 'noOperator(0)' and
        cannot be changed while this row is active, i.e., the value of
        numIpExternStatus in the same row has the value 'active(1)'.
        
        'noOperator(0)', which is the default value, means that no
        comparison is to be made with the source TCP/UDP port number.
        
        eq(1) means equal, This operators are using the ipExternSrcPort1 
        object as an operand which is the only one needed. 
        
        range(3) means that it compares the port value between two 
        numbers, so this operator needs 2 operands. One operand is 
        the starting port number of the range which is ipExternSrcPort1 
        object, and the other operand is the ending port number of the 
        range which the ipExternSrcPort2 object is in.
        
        Now support(3)eq,(5)range."
            ::= { ipExternAclEntry 11 }

--xxx.100.10.1.3.4.1.12
        ipExternSrcPort1 OBJECT-TYPE
            SYNTAX INTEGER(0..65535)          
            MAX-ACCESS  read-write
            STATUS  current
            DESCRIPTION
                "The source port number of the TCP or UDP protocol. If the
        numIpExternSrcOP object in the same row is range(5), this
        object will be the starting port number of the port range.
        This object cannot be configured if numIpExternStatus in the 
        same row is active(1) or numIpExternSrcOP in the same row
        is noOperator(0)."
            ::= { ipExternAclEntry 12 }

--xxx.100.10.1.3.4.1.13       
	ipExternSrcPort2 OBJECT-TYPE
    	   SYNTAX INTEGER(0..65535)
    	   MAX-ACCESS read-write
    	   STATUS current
    	   DESCRIPTION
        	"The source port number of the TCP or UDP protocol. If the
        numIpExternSrcOP object in the same row is range(5), this
        object will be the ending port number of the port range.
        This object cannot be configured if numIpExternStatus in the 
        same row is active(1) or numIpExternSrcOP in the same row
        is not range(5)."
    ::= { ipExternAclEntry 13 }            

--xxx.100.10.1.3.4.1.14 
        ipExternDstOp OBJECT-TYPE
            SYNTAX INTEGER{
                noOperator(0),
			        	eq(1),
			        	range(2)
        	}           
            MAX-ACCESS  read-write
            STATUS  current
            DESCRIPTION
                "Indicates how a packet's Destination TCP/UDP port number is
        to be compared.
        
        If the numIpExternProtocol object in the same row does not
        indicate TCP or UDP, this object has to be 'noOperator(0)' and
        cannot be changed while this row is active, i.e., the value of
        numIpExternStatus in the same row has the value 'active(1)'.
        
        'noOperator(0)', which is the default value, means that no
        comparison is to be made with the source TCP/UDP port number.
         eq(1)means equal, This operators are using the numIpExternDestPort 
         object as an operand which is the only one needed. 
        
        range(5) means that it compares the port value between two 
        numbers, so this operator needs 2 operands. One operand is 
        the starting port number of the range which is numIpExternSrcPort 
        object, and the other operand is the ending port number of the 
        range which the numIpExternDestPortRange object is in.
        
        Now support(3)eq,(5)range."
            ::= { ipExternAclEntry 14 }

--xxx.100.10.1.3.4.1.15
        ipExternDstPort1 OBJECT-TYPE
            SYNTAX INTEGER(0..65535)          
            MAX-ACCESS  read-write
            STATUS  current
            DESCRIPTION
                "The source port number of the TCP or UDP protocol. If the
        numIpExternDestOP object in the same row is range(5), this
        object will be the starting port number of the port range.
        This object cannot be configured if numIpExternStatus in the 
        same row is active(1) or numIpExternDestOP in the same row
        is noOperator(0)."
            ::= { ipExternAclEntry 15 }

--xxx.100.10.1.3.4.1.16       
	ipExternDstPort2 OBJECT-TYPE
    	   SYNTAX INTEGER(0..65535)
    	   MAX-ACCESS read-write
    	   STATUS current
    	   DESCRIPTION
        	"The source port number of the TCP or UDP protocol. If the
        numIpExternDestOP object in the same row is range(5), this
        object will be the ending port number of the port range.
        This object cannot be configured if numIpExternStatus in the 
        same row is active(1) or numIpExternDestOP in the same row
        is not range(5)."
    		::= { ipExternAclEntry 16 }
     

--xxx.100.10.1.3.4.1.17
        ipExternStatus OBJECT-TYPE
            SYNTAX  INTEGER
            	    {
            	    	createAndGo(0),
               		active(1),
               		destroy(2)
            	    }
            MAX-ACCESS  read-write
            STATUS  current
            DESCRIPTION
                " now state of the access-list."
            ::= { ipExternAclEntry 17 } 
            
--*************************************************************************************************************************************           
--*************************************************************************************************************************************           
--xxx.100.10.1.3.5
macStandardAclTable OBJECT-TYPE
    SYNTAX  SEQUENCE OF MacStandardAclEntry
    MAX-ACCESS  not-accessible
    STATUS  current
            DESCRIPTION
                "mac Standard Acl Table"
            ::= { aclConfig 5  } 
            
--xxx.100.10.1.3.5.1
    macStandardAclEntry OBJECT-TYPE
        SYNTAX  MacStandardAclEntry
        MAX-ACCESS  not-accessible
        STATUS  current
        DESCRIPTION
            "mac standard  Table's Entry"
        INDEX   { macStandardIndex, macStandardSubIndex}
        ::= { macStandardAclTable 1 }

    MacStandardAclEntry
        ::= SEQUENCE
            {
               macStandardIndex        INTEGER,
               macStandardSubIndex     INTEGER,
               macStandardPriority     INTEGER,
               macStandardAct		       INTEGER,
               macStandardSrcMac		     DisplayString,
               macStandardSrcMacWild    DisplayString,
               macStandardStatus       INTEGER
            }
            
--xxx.100.10.1.3.5.1.1            
        macStandardIndex OBJECT-TYPE
            SYNTAX  INTEGER 
            MAX-ACCESS  read-only
            STATUS  current
            DESCRIPTION
                "The index of mac-standard-acl group ."
            ::= { macStandardAclEntry 1 }
            
 --xxx.100.10.1.3.5.1.2            
        macStandardSubIndex OBJECT-TYPE
            SYNTAX  INTEGER 
            MAX-ACCESS  read-only
            STATUS  current
            DESCRIPTION
                "The index of mac-standard-acl rule ."
            ::= { macStandardAclEntry 2 }
            
 --xxx.100.10.1.3.5.1.3
        macStandardPriority OBJECT-TYPE
            SYNTAX  INTEGER 
            MAX-ACCESS read-write
            STATUS  current
            DESCRIPTION
              "The priority of standard mac acl's rule,it is not supported now."
            ::= { macStandardAclEntry 3 } 
                                  
 --xxx.100.10.1.3.5.1.4
        macStandardAct OBJECT-TYPE
            SYNTAX  INTEGER
              	    {
            	    	 deny(0),
               		   permit(1)
            	      }            
            MAX-ACCESS  read-write
            STATUS  current
            DESCRIPTION
                " The action of acl rule."
            ::= { macStandardAclEntry 4 }

 --xxx.100.10.1.3.5.1.5
        macStandardSrcMac OBJECT-TYPE
            SYNTAX  DisplayString(SIZE(17))            
            MAX-ACCESS  read-write
            STATUS  current
            DESCRIPTION
                " Source Mac-address of basic acl rule,for example : ff-ff-ff-ff-ff-00."
            ::= { macStandardAclEntry 5 }
            
 --xxx.100.10.1.3.5.1.6
        macStandardSrcMacWild OBJECT-TYPE
            SYNTAX  DisplayString(SIZE(17))           
            MAX-ACCESS  read-write
            STATUS  current
            DESCRIPTION
                " Source Mac-address's anti-mask of basic acl rule,for example : ff-ff-ff-ff-00-00."
            ::= { macStandardAclEntry 6 }

 --xxx.100.10.1.3.5.1.7
        macStandardStatus OBJECT-TYPE
            SYNTAX  INTEGER
            	    {
            	    	createAndGo(0),
               		 active(1),
               		 destroy(2)
            	    }
            MAX-ACCESS  read-write
            STATUS  current
            DESCRIPTION
                " status of the access-list."
            ::= { macStandardAclEntry 7} 



--******************************************************************************************************** 
--xxx.100.10.1.3.6
 macExternAclTable OBJECT-TYPE
    SYNTAX  SEQUENCE OF MacExternAclEntry
    MAX-ACCESS  not-accessible
    STATUS  current
            DESCRIPTION
                "mac extern Acl Table"
            ::= { aclConfig 6  } 
                      
 --xxx.100.10.1.3.6.1
    macExternAclEntry OBJECT-TYPE
        SYNTAX  MacExternAclEntry
        MAX-ACCESS  not-accessible
        STATUS  current
        DESCRIPTION
            "mac extern  Table's Entry"
        INDEX   { macExternIndex, macExternSubIndex}
        ::= { macExternAclTable 1 }

    MacExternAclEntry
        ::= SEQUENCE
            {
               macExternIndex        INTEGER,
               macExternSubIndex       INTEGER,
               macExternPriority     INTEGER,
               macExternAct		       INTEGER,            
               macExternSrcMac		     DisplayString,
               macExternSrcMacWild    DisplayString,
               macExternDstMac       DisplayString,
               macExternDstMacWild   DisplayString,
               macExternPacketType   INTEGER,
               macExternEtherType    INTEGER,
               macExternEtherTypeWild    INTEGER,
               macExternCos	           INTEGER,
               macExternCosWild        INTEGER,
               macExternVlanId		     INTEGER,
               macExternVlanIdWild     INTEGER,
               macExternStatus       INTEGER
            }
                  
 --xxx.100.10.1.3.6.1.1
        macExternIndex OBJECT-TYPE
            SYNTAX  INTEGER 
            MAX-ACCESS read-only
            STATUS  current
            DESCRIPTION
                "The index of Mac-Extern-acl group."
            ::= { macExternAclEntry 1 }
            
 --xxx.100.10.1.3.6.1.2
      macExternSubIndex OBJECT-TYPE
           SYNTAX  INTEGER
           MAX-ACCESS  read-only
           STATUS  current
           DESCRIPTION
               " The index of Mac-Extern-acl rule."
          ::= { macExternAclEntry 2 }

 --xxx.100.10.1.3.6.1.3
      macExternPriority  OBJECT-TYPE
           SYNTAX  INTEGER
           MAX-ACCESS  read-write
           STATUS  current
           DESCRIPTION
               " The priority of extern mac acl's rule,it is not supported now."
          ::= { macExternAclEntry 3 }
          
 --xxx.100.10.1.3.6.1.4
        macExternAct OBJECT-TYPE
            SYNTAX  INTEGER 
             	    {
            	    	deny(0),
               		  permit(1)
            	    }            
            MAX-ACCESS  read-write
            STATUS  current
            DESCRIPTION
                " The action of acl rule."
            ::= { macExternAclEntry 4 }
                        
 --xxx.100.10.1.3.6.1.5
        macExternSrcMac OBJECT-TYPE
            SYNTAX  DisplayString(SIZE(17))            
            MAX-ACCESS  read-write
            STATUS  current
            DESCRIPTION
                " Source Mac-address of advanced acl rule,for example : ff-ff-ff-ff-ff-00."
            ::= { macExternAclEntry 5 }
            
 --xxx.100.10.1.3.6.1.6
        macExternSrcMacWild OBJECT-TYPE
            SYNTAX  DisplayString(SIZE(17))           
            MAX-ACCESS  read-write
            STATUS  current
            DESCRIPTION
                " Source Mac-address's anti-mask  of advanced acl rule,for example : ff-ff-ff-ff-00-00."
            ::= { macExternAclEntry 6 }

 --xxx.100.10.1.3.6.1.7
        macExternDstMac OBJECT-TYPE
            SYNTAX  DisplayString(SIZE(17))            
            MAX-ACCESS  read-write
            STATUS  current
            DESCRIPTION
                " Destination Mac-address of advanced acl rule,for example : ff-ff-ff-ff-ff-00."
            ::= { macExternAclEntry 7 }
            
 --xxx.100.10.1.3.6.1.8
        macExternDstMacWild OBJECT-TYPE
            SYNTAX  DisplayString(SIZE(17))           
            MAX-ACCESS  read-write
            STATUS  current
            DESCRIPTION
                " Destination Mac-address's anti-mask  of advanced acl rule,for example : ff-ff-ff-ff-00-00."
            ::= { macExternAclEntry 8 }    
            
 --xxx.100.10.1.3.6.1.9
	macExternPacketType OBJECT-TYPE
    	    SYNTAX INTEGER
    	    MAX-ACCESS read-write
    	    STATUS current
    	    DESCRIPTION
                "Indicates the message type of packets.none(0),untagged-eth2(1),
                untagged-802.3(2),tagged-eth2(3),tagged-802.3(4)"
    	    ::= { macExternAclEntry 9 }

 --xxx.100.10.1.3.6.1.10
	macExternEtherType OBJECT-TYPE
    	    SYNTAX INTEGER(1536..65535)
    	    MAX-ACCESS read-write
    	    STATUS current
    	    DESCRIPTION
                "Value of the ethertype"
    	    ::= { macExternAclEntry 10 }   

 --xxx.100.10.1.3.6.1.11
	macExternEtherTypeWild OBJECT-TYPE
    	    SYNTAX INTEGER(0..65535)
    	    MAX-ACCESS read-write
    	    STATUS current
    	    DESCRIPTION
                "Anti-mask of the ethertype"
    	    ::= { macExternAclEntry 11 }

 --xxx.100.10.1.3.6.1.12
	macExternCos OBJECT-TYPE
    	    SYNTAX INTEGER(0..7)
    	    MAX-ACCESS read-write
    	    STATUS current
    	    DESCRIPTION
                "value of the cos"
    	    ::= { macExternAclEntry 12 }

 --xxx.100.10.1.3.6.1.13
	macExternCosWild OBJECT-TYPE
    	    SYNTAX INTEGER(0..7)
    	    MAX-ACCESS read-write
    	    STATUS current
    	    DESCRIPTION
                "Anti-mask of the cos"
    	    ::= { macExternAclEntry 13 }

 --xxx.100.10.1.3.6.1.14
	macExternVlanId OBJECT-TYPE
    	    SYNTAX INTEGER(1..4094)
    	    MAX-ACCESS read-write
    	    STATUS current
    	    DESCRIPTION
                "vlan id"
    	    ::= { macExternAclEntry 14 }

 --xxx.100.10.1.3.6.1.15
	macExternVlanIdWild OBJECT-TYPE
    	    SYNTAX INTEGER(0..4095)
    	    MAX-ACCESS read-write
    	    STATUS current
    	    DESCRIPTION
                "Anti-mask of the vlan id"
    	    ::= { macExternAclEntry 15 }
    	        	        	        	        	        	             
 --xxx.100.10.1.3.6.1.16
        macExternStatus OBJECT-TYPE
            SYNTAX  INTEGER
            	    {
            	    	createAndGo(0),
               		  active(1),
               		  destroy(2)
            	    }
            MAX-ACCESS  read-write
            STATUS  current
            DESCRIPTION
                " now state of the access-list."
            ::= { macExternAclEntry 16 }            
--********************************************************************************************************

--xxx.100.10.1.3.7
ipv6StandardAclTable OBJECT-TYPE
    SYNTAX  SEQUENCE OF Ipv6StandardAclEntry
    MAX-ACCESS  not-accessible
    STATUS  current
            DESCRIPTION
                "ipv6 Standard Acl Table"
            ::= { aclConfig 7 } 
            
--xxx.100.10.1.3.7.1
    ipv6StandardAclEntry OBJECT-TYPE
        SYNTAX  Ipv6StandardAclEntry
        MAX-ACCESS  not-accessible
        STATUS  current
        DESCRIPTION
            "ipv6 standard  Table's Entry"
        INDEX   { ipv6StandardIndex, ipv6StandardSubIndex}
        ::= { ipv6StandardAclTable 1 }

    Ipv6StandardAclEntry
        ::= SEQUENCE
            {
               ipv6StandardIndex        INTEGER,
               ipv6StandardSubIndex     INTEGER,
               ipv6StandardPriority     INTEGER,
               ipv6StandardAct		      INTEGER,
               ipv6StandardSrcIp		    DisplayString,
               ipv6StandardSrcPrefixLen    INTEGER,
               ipv6StandardStatus       INTEGER
            }
                                                           
--xxx.100.10.1.3.7.1.1
        ipv6StandardIndex OBJECT-TYPE
            SYNTAX  INTEGER 
            MAX-ACCESS read-only
            STATUS  current
            DESCRIPTION
                "The index of ipv6-standard-acl group."
            ::= { ipv6StandardAclEntry 1 }
            
--xxx.100.10.1.3.7.1.2
        ipv6StandardSubIndex OBJECT-TYPE
            SYNTAX  INTEGER 
            MAX-ACCESS read-only
            STATUS  current
            DESCRIPTION
                "The index of ipv6-standard-acl rule."
            ::= { ipv6StandardAclEntry 2 }

--xxx.100.10.1.3.7.1.3
        ipv6StandardPriority OBJECT-TYPE
            SYNTAX  INTEGER 
            MAX-ACCESS read-write
            STATUS  current
            DESCRIPTION
                "The priority of standard ipv6 acl's rule,it is not supported now."
            ::= { ipv6StandardAclEntry 3 }
            
                        
--xxx.100.10.1.3.7.1.4
        ipv6StandardAct OBJECT-TYPE
            SYNTAX  INTEGER 
             	    {
            	    	deny(0),
               		  permit(1)
            	    }            
            MAX-ACCESS  read-write
            STATUS  current
            DESCRIPTION
                " The action of acl rule."
            ::= { ipv6StandardAclEntry 4 }

            
--xxx.100.10.1.3.7.1.5
        ipv6StandardSrcIp OBJECT-TYPE
            SYNTAX  DisplayString(SIZE(1..40))            
            MAX-ACCESS  read-write
            STATUS  current
            DESCRIPTION
                " Source IPV6-address of basic acl rule,for example : 3ffe:506::100."
            ::= { ipv6StandardAclEntry 5 }
            
--xxx.100.10.1.3.7.1.6
       ipv6StandardSrcPrefixLen OBJECT-TYPE
            SYNTAX  INTEGER(0..128)           
            MAX-ACCESS  read-write
            STATUS  current
            DESCRIPTION
                " Source IPV6-address prefix length of basic acl rule."
            ::= { ipv6StandardAclEntry 6 }

--xxx.100.10.1.3.7.1.7
        ipv6StandardStatus OBJECT-TYPE
            SYNTAX  INTEGER
            	    {
            	    	createAndGo(0),
               		  active(1),
               		  destroy(2)
            	    }
            MAX-ACCESS  read-write
            STATUS  current
            DESCRIPTION
                " now state of the access-list."
            ::= { ipv6StandardAclEntry 7 } 

--********************************************************************************************************
            
--xxx.100.10.1.3.8
ipv6ExternAclTable OBJECT-TYPE
    SYNTAX  SEQUENCE OF Ipv6ExternAclEntry
    MAX-ACCESS  not-accessible
    STATUS  current
            DESCRIPTION
                "ipv6 extern Acl Table"
            ::= { aclConfig 8  } 
            
--xxx.100.10.1.3.8.1
    ipv6ExternAclEntry OBJECT-TYPE
        SYNTAX  Ipv6ExternAclEntry
        MAX-ACCESS  not-accessible
        STATUS  current
        DESCRIPTION
            "ipv6 extern Table's Entry"
        INDEX   { ipv6ExternIndex,ipv6ExternSubIndex }
        ::= { ipv6ExternAclTable 1 }

    Ipv6ExternAclEntry
        ::= SEQUENCE
            {
               ipv6ExternIndex        INTEGER,
               ipv6ExternSubIndex     INTEGER,
               ipv6ExternPriority     INTEGER,               
               ipv6ExternAct		      INTEGER,
               ipv6ExternProtocal     INTEGER,
               ipv6ExternSrcIp		    DisplayString,
               ipv6ExternSrcPreLen    INTEGER,
               ipv6ExternDstIp        DisplayString,
               ipv6ExternDstPreLen    INTEGER,
               ipv6ExternTimeRangeName  DisplayString,              
               ipv6ExternSrcOp        INTEGER,
               ipv6ExternSrcPort1     INTEGER,
               ipv6ExternSrcPort2     INTEGER,
               ipv6ExternDstOp        INTEGER,
               ipv6ExternDstPort1     INTEGER,
               ipv6ExternDstPort2     INTEGER,
               ipv6ExternStatus         INTEGER
            }
            
--xxx.100.10.1.3.8.1.1
        ipv6ExternIndex OBJECT-TYPE
            SYNTAX  INTEGER 
            MAX-ACCESS read-write
            STATUS  current
            DESCRIPTION
                "The index of ipv6-Extern-acl group ."
            ::= { ipv6ExternAclEntry 1 }
            
--xxx.100.10.1.3.8.1.2
        ipv6ExternSubIndex OBJECT-TYPE
            SYNTAX  INTEGER 
            MAX-ACCESS read-write
            STATUS  current
            DESCRIPTION
                "The index of ipv6-Extern-acl rule ."
            ::= { ipv6ExternAclEntry 2 }
            
--xxx.100.10.1.3.8.1.3
        ipv6ExternPriority OBJECT-TYPE
            SYNTAX  INTEGER 
            MAX-ACCESS read-write
            STATUS  current
            DESCRIPTION
              "The priority of extern ipv6 acl's rule,it is not supported now."
            ::= { ipv6ExternAclEntry 3 } 
                       
--xxx.100.10.1.3.8.1.4
        ipv6ExternAct OBJECT-TYPE
            SYNTAX  INTEGER 
             	    {
            	    	deny(0),
               		permit(1)
            	    }            
            MAX-ACCESS  read-write
            STATUS  current
            DESCRIPTION
                " The action of acl rule."
            ::= { ipv6ExternAclEntry 4 }

--xxx.100.10.1.3.8.1.10
        ipv6ExternProtocal OBJECT-TYPE
            SYNTAX INTEGER(0..255)           
            MAX-ACCESS  read-write
            STATUS  current
            DESCRIPTION
                "The protocol number field in the IP header used to indicate
        the higher layer protocol as specified .  
        
        For example :
        0 is IP, 1 is ICMP, 2 is IGMP, 4 is IP in IP encapsulation,
        6 is TCP, 9 is IGRP, 17 is UDP, 47 is GRE, 50 is ESP, 51 is AH,
        88 is EIGRP, 89 is OSPF, 94 is KA9Q/NOS compatible IP over IP,
        103 is PIMv2, 108 is PCP"
            ::= { ipv6ExternAclEntry 5 }
            
--xxx.100.10.1.3.8.1.5
        ipv6ExternSrcIp OBJECT-TYPE
            SYNTAX  DisplayString(SIZE(1..40))            
            MAX-ACCESS  read-write
            STATUS  current
            DESCRIPTION
                " Source IPV6-address of advanced acl rule,for example : 3ffe:506::100."
            ::= { ipv6ExternAclEntry 6 }
            
--xxx.100.10.1.3.8.1.6
        ipv6ExternSrcPreLen OBJECT-TYPE
            SYNTAX  INTEGER(0..128)           
            MAX-ACCESS  read-write
            STATUS  current
            DESCRIPTION
                " Source IP-address prefix length of advanced acl rule."
            ::= { ipv6ExternAclEntry 7 }

            
--xxx.100.10.1.3.8.1.7
        ipv6ExternDstIp OBJECT-TYPE
            SYNTAX  DisplayString(SIZE(1..40))            
            MAX-ACCESS  read-write
            STATUS  current
            DESCRIPTION
                " Destination IPV6-address of advanced acl rule,for example : 3ffe:506::100."
            ::= { ipv6ExternAclEntry 8 }
            
--xxx.100.10.1.3.8.1.8
        ipv6ExternDstPreLen OBJECT-TYPE
            SYNTAX  INTEGER(0..128)           
            MAX-ACCESS  read-write
            STATUS  current
            DESCRIPTION
                " Destination IPV6-address prefix length of advanced acl rule."
            ::= { ipv6ExternAclEntry 9 }


--xxx.100.10.1.3.8.1.9
        ipv6ExternTimeRangeName OBJECT-TYPE
            SYNTAX DisplayString          
            MAX-ACCESS  read-write
            STATUS  current
            DESCRIPTION
                "The Time-range of advanced acl rule."
            ::= { ipv6ExternAclEntry 10 }


            
--xxx.100.10.1.3.8.1.11
        ipv6ExternSrcOp OBJECT-TYPE
            SYNTAX INTEGER{
                noOperator(0),
        	      eq(3),
        	      range(5)
        	}           
            MAX-ACCESS  read-write
            STATUS  current
            DESCRIPTION
                "Indicates how a packet's source  TCP/UDP port number is
        to be compared.
        
        If the ipv6ExternProtocal object in the same row does not
        indicate TCP or UDP, this object has to be 'noOperator(0)' and
        cannot be changed while this row is active, i.e., the value of
        ipv6ExternStatus in the same row has the value 'active(1)'.
        
        'noOperator(0)', which is the default value, means that no
        comparison is to be made with the source TCP/UDP port number.
        
        eq(3) means equal,range(5) means that it compares the port value between two 
        numbers, so this operator needs 2 operands. One operand is 
        the starting port number of the range which is ipv6ExternSrcPort1 
        object, and the other operand is the ending port number of the 
        range which the ipv6ExternSrcPort2 object is in."
            ::= { ipv6ExternAclEntry 11 }

--xxx.100.10.1.3.8.1.12
        ipv6ExternSrcPort1 OBJECT-TYPE
            SYNTAX INTEGER(0..65535)          
            MAX-ACCESS  read-write
            STATUS  current
            DESCRIPTION
                "The source port number of the TCP or UDP protocol. If the
        ipv6ExternSrcOp object in the same row is range(5), this
        object will be the starting port number of the port range.
        This object cannot be configured if ipv6ExternStatus in the 
        same row is active(1) or ipv6ExternSrcOp in the same row
        is noOperator(0)."
            ::= { ipv6ExternAclEntry 12 }

--xxx.100.10.1.3.8.1.13       
	ipv6ExternSrcPort2 OBJECT-TYPE
    	   SYNTAX INTEGER(0..65535)
    	   MAX-ACCESS read-write
    	   STATUS current
    	   DESCRIPTION
        	"The source port number of the TCP or UDP protocol. If the
        ipv6ExternSrcOp object in the same row is range(5), this
        object will be the ending port number of the port range.
        This object cannot be configured if ipv6ExternStatus in the 
        same row is active(1) or ipv6ExternSrcOp in the same row
        is not range(5)."
    ::= { ipv6ExternAclEntry 13 }            

--xxx.100.10.1.3.8.1.14 
        ipv6ExternDstOp OBJECT-TYPE
            SYNTAX INTEGER{
                noOperator(0),
              	eq(3),        	    
        	      range(5)
        	 }           
            MAX-ACCESS  read-write
            STATUS  current
            DESCRIPTION
                "Indicates how a packet's Destination TCP/UDP port number is
        to be compared.
        
        If the ipv6ExternProtocal object in the same row does not
        indicate TCP or UDP, this object has to be 'noOperator(0)' and
        cannot be changed while this row is active, i.e., the value of
        ipv6ExternStatus in the same row has the value 'active(1)'.
        
        'noOperator(0)', which is the default value, means that no
        comparison is to be made with the source TCP/UDP port number.
        
        eq(3) means equal,range(5) means that it compares the port value between two 
        numbers, so this operator needs 2 operands. One operand is 
        the starting port number of the range which is ipv6ExternDstPort1 
        object, and the other operand is the ending port number of the 
        range which the ipv6ExternDstPort2 object is in."
            ::= { ipv6ExternAclEntry 14 }

--xxx.100.10.1.3.8.1.15
        ipv6ExternDstPort1 OBJECT-TYPE
            SYNTAX INTEGER(0..65535)          
            MAX-ACCESS  read-write
            STATUS  current
            DESCRIPTION
                "The Destination port number of the TCP or UDP protocol. If the
        ipv6ExternDstOp object in the same row is range(5), this
        object will be the starting port number of the port range.
        This object cannot be configured if ipv6ExternStatus in the 
        same row is active(1) or ipv6ExternDstOp in the same row
        is noOperator(0)."
            ::= { ipv6ExternAclEntry 15 }

--xxx.100.10.1.3.8.1.16       
	ipv6ExternDstPort2 OBJECT-TYPE
    	   SYNTAX INTEGER(0..65535)
    	   MAX-ACCESS read-write
    	   STATUS current
    	   DESCRIPTION
        	"The Destination port number of the TCP or UDP protocol. If the
        ipv6ExternDstOp object in the same row is range(5), this
        object will be the ending port number of the port range.
        This object cannot be configured if ipv6ExternStatus in the 
        same row is active(1) or ipv6ExternDstOp in the same row
        is not range(5)."
    		::= { ipv6ExternAclEntry 16 }
     

--xxx.100.10.1.3.8.1.17
        ipv6ExternStatus OBJECT-TYPE
            SYNTAX  INTEGER
            	    {
            	    	createAndGo(0),
               		active(1),
               		destroy(2)
            	    }
            MAX-ACCESS  read-write
            STATUS  current
            DESCRIPTION
                " status of ipv6ExternAclTable."
            ::= { ipv6ExternAclEntry 17 } 

--********************************************************************************************************
--xxx.100.10.1.3.9
macIpExternAclTable OBJECT-TYPE
    SYNTAX  SEQUENCE OF MacIpExternAclEntry
    MAX-ACCESS  not-accessible
    STATUS  current
            DESCRIPTION
                "mac-ip extern Acl Table"
            ::= { aclConfig 9  } 
            
--xxx.100.10.1.3.9.1
    macIpExternAclEntry OBJECT-TYPE
        SYNTAX  MacIpExternAclEntry
        MAX-ACCESS  not-accessible
        STATUS  current
        DESCRIPTION
            "mac-ip extern Table's Entry"
        INDEX   { macIpExternIndex,macIpExternSubIndex }
        ::= { macIpExternAclTable 1 }

    MacIpExternAclEntry
        ::= SEQUENCE
            {
               macIpExternIndex        INTEGER,
               macIpExternSubIndex     INTEGER,
               macIpExternPriority     INTEGER,               
               macIpExternAct		      INTEGER,
               macIpExternProtocal     Integer32,
               macIpExternSrcMac		     DisplayString,
               macIpExternSrcMacWild    DisplayString,
               macIpExternDstMac       DisplayString,
               macIpExternDstMacWild   DisplayString,
               macIpExternSrcIp		    IpAddress,
               macIpExternSrcIpWild    IpAddress,
               macIpExternDstIp        IpAddress,
               macIpExternDstIpWild    IpAddress,
               macIpExternTimeRangeName  DisplayString,
               macIpExternSrcOp        INTEGER,
               macIpExternSrcPort1     INTEGER,
               macIpExternSrcPort2     INTEGER,
               macIpExternDstOp        INTEGER,
               macIpExternDstPort1     INTEGER,
               macIpExternDstPort2     INTEGER,
               macIpExternPrecedence    INTEGER,
               macIpExternTos           INTEGER,
               macIpExternStatus         INTEGER,
               macIpExternVlanId         INTEGER,
               macIpExternVlanIdWild     INTEGER
            }
            
--xxx.100.10.1.3.9.1.1
        macIpExternIndex OBJECT-TYPE
            SYNTAX  INTEGER 
            MAX-ACCESS read-only
            STATUS  current
            DESCRIPTION
                "The index of macIp-Extern-acl group ."
            ::= { macIpExternAclEntry 1 }
            
--xxx.100.10.1.3.9.1.2
        macIpExternSubIndex OBJECT-TYPE
            SYNTAX  INTEGER 
            MAX-ACCESS read-only
            STATUS  current
            DESCRIPTION
                "The index of macIp-Extern-acl rule ."
            ::= { macIpExternAclEntry 2 }
            
--xxx.100.10.1.3.9.1.3
        macIpExternPriority OBJECT-TYPE
            SYNTAX  INTEGER 
            MAX-ACCESS read-write
            STATUS  current
            DESCRIPTION
              "The priority of extern macIp acl's rule,it is not supported now."
            ::= { macIpExternAclEntry 3 } 
                       
--xxx.100.10.1.3.9.1.4
        macIpExternAct OBJECT-TYPE
            SYNTAX  INTEGER 
             	    {
            	    	deny(0),
               		  permit(1)
            	    }            
            MAX-ACCESS  read-write
            STATUS  current
            DESCRIPTION
                " The action of acl rule."
            ::= { macIpExternAclEntry 4 }

--xxx.100.10.1.3.9.1.5
        macIpExternProtocal OBJECT-TYPE
            SYNTAX Integer32(0..255|65535)           
            MAX-ACCESS  read-write
            STATUS  current
            DESCRIPTION
                "The protocol number field in the IP header used to indicate
        the higher layer protocol as specified in RFC 1700. A value 
        value of 65535 matches every IP packet. 
        
        For example :
        1 is ICMP, 2 is IGMP, 4 is IP in IP encapsulation,
        6 is TCP, 9 is IGRP, 17 is UDP, 47 is GRE, 50 is ESP, 51 is AH,
        88 is EIGRP, 89 is OSPF, 94 is KA9Q/NOS compatible IP over IP,
        103 is PIMv2, 108 is PCP, 65535 is ip."
            ::= { macIpExternAclEntry 5}


 --xxx.100.10.1.3.9.1.6
        macIpExternSrcMac OBJECT-TYPE
            SYNTAX  DisplayString(SIZE(17))            
            MAX-ACCESS  read-write
            STATUS  current
            DESCRIPTION
                " Source Mac-address of advanced acl rule,for example : ff-ff-ff-ff-ff-00."
            ::= { macIpExternAclEntry 6 }
            
 --xxx.100.10.1.3.9.1.7
        macIpExternSrcMacWild OBJECT-TYPE
            SYNTAX  DisplayString(SIZE(17))           
            MAX-ACCESS  read-write
            STATUS  current
            DESCRIPTION
                " Source Mac-address's anti-mask  of advanced acl rule,for example : ff-ff-ff-ff-00-00."
            ::= { macIpExternAclEntry 7 }

 --xxx.100.10.1.3.9.1.8
        macIpExternDstMac OBJECT-TYPE
            SYNTAX  DisplayString(SIZE(17))            
            MAX-ACCESS  read-write
            STATUS  current
            DESCRIPTION
                " Destination Mac-address of advanced acl rule,for example : ff-ff-ff-ff-ff-00."
            ::= { macIpExternAclEntry 8 }
            
 --xxx.100.10.1.3.9.1.9
        macIpExternDstMacWild OBJECT-TYPE
            SYNTAX  DisplayString(SIZE(17))           
            MAX-ACCESS  read-write
            STATUS  current
            DESCRIPTION
                " Destination Mac-address's anti-mask  of advanced acl rule,for example : ff-ff-ff-ff-00-00."
            ::= { macIpExternAclEntry 9 }    
            
                        
--xxx.100.10.1.3.9.1.10
        macIpExternSrcIp OBJECT-TYPE
            SYNTAX  IpAddress            
            MAX-ACCESS  read-write
            STATUS  current
            DESCRIPTION
                " Source IP-address of advanced acl rule,for example 10.1.1.0 ."
            ::= { macIpExternAclEntry 10}
            
--xxx.100.10.1.3.9.1.11
        macIpExternSrcIpWild OBJECT-TYPE
            SYNTAX  IpAddress           
            MAX-ACCESS  read-write
            STATUS  current
            DESCRIPTION
                " Source IP-address wild  of advanced acl rule,for example 0.0.0.255 ."
            ::= { macIpExternAclEntry 11 }

            
--xxx.100.10.1.3.9.1.12
        macIpExternDstIp OBJECT-TYPE
            SYNTAX  IpAddress            
            MAX-ACCESS  read-write
            STATUS  current
            DESCRIPTION
                " Destination IP-address of advanced acl rule,for example 10.1.1.0 ."
            ::= { macIpExternAclEntry 12 }
            
--xxx.100.10.1.3.9.1.13
        macIpExternDstIpWild OBJECT-TYPE
            SYNTAX  IpAddress           
            MAX-ACCESS  read-write
            STATUS  current
            DESCRIPTION
                " Destination IP-address wild  of advanced acl rule,for example 0.0.0.255 ."
            ::= { macIpExternAclEntry 13 }


--xxx.100.10.1.3.9.1.14
         macIpExternTimeRangeName OBJECT-TYPE
            SYNTAX DisplayString(SIZE (1..64))    
            MAX-ACCESS  read-write
            STATUS  current
            DESCRIPTION
                "The Time-range of advanced acl rule."
            ::= { macIpExternAclEntry 14 }
            
--xxx.100.10.1.3.9.1.15
        macIpExternSrcOp OBJECT-TYPE
            SYNTAX INTEGER{
                noOperator(0),
			        	eq(3),
			        	range(5)
        	}           
            MAX-ACCESS  read-write
            STATUS  current
            DESCRIPTION
                "Indicates how a packet's source TCP/UDP port number is
        to be compared.
        
        If the macIpExternProtocal object in the same row does not
        indicate TCP or UDP, this object has to be 'noOperator(0)' and
        cannot be changed while this row is active, i.e., the value of
        macIpExternStatus in the same row has the value 'active(1)'.
        
        'noOperator(0)', which is the default value, means that no
        comparison is to be made with the source TCP/UDP port number.
        
        eq(3) means equal, This operators are using the macIpExternSrcPort1 
        object as an operand which is the only one needed. 
        
        range(5) means that it compares the port value between two 
        numbers, so this operator needs 2 operands. One operand is 
        the starting port number of the range which is macIpExternSrcPort1 
        object, and the other operand is the ending port number of the 
        range which the macIpExternSrcPort2 object is in.
        
        Now support(3)eq,(5)range."
            ::= { macIpExternAclEntry 15 }

--xxx.100.10.1.3.9.1.16
        macIpExternSrcPort1 OBJECT-TYPE
            SYNTAX INTEGER(0..65535)          
            MAX-ACCESS  read-write
            STATUS  current
            DESCRIPTION
                "The source port number of the TCP or UDP protocol. If the
        macIpExternSrcOP object in the same row is range(5), this
        object will be the starting port number of the port range.
        This object cannot be configured if macIpExternStatus in the 
        same row is active(1) or numIpExternSrcOP in the same row
        is noOperator(0)."
            ::= { macIpExternAclEntry 16 }

--xxx.100.10.1.3.9.1.17       
	macIpExternSrcPort2 OBJECT-TYPE
    	   SYNTAX INTEGER(0..65535)
    	   MAX-ACCESS read-write
    	   STATUS current
    	   DESCRIPTION
        	"The source port number of the TCP or UDP protocol. If the
        macIpExternSrcOP object in the same row is range(5), this
        object will be the ending port number of the port range.
        This object cannot be configured if numIpExternStatus in the 
        same row is active(1) or macIpExternSrcOP in the same row
        is not range(5)."
    ::= { macIpExternAclEntry 17 }            

--xxx.100.10.1.3.9.1.18 
        macIpExternDstOp OBJECT-TYPE
            SYNTAX INTEGER{
                noOperator(0),
			        	eq(1),
			        	range(2)
        	}           
            MAX-ACCESS  read-write
            STATUS  current
            DESCRIPTION
                "Indicates how a packet's Destination TCP/UDP port number is
        to be compared.
        
        If the macIpExternProtocol object in the same row does not
        indicate TCP or UDP, this object has to be 'noOperator(0)' and
        cannot be changed while this row is active, i.e., the value of
        macIpExternStatus in the same row has the value 'active(1)'.
        
        'noOperator(0)', which is the default value, means that no
        comparison is to be made with the source TCP/UDP port number.
         eq(3)means equal, This operators are using the macIpExternDstPort 
         object as an operand which is the only one needed. 
        
        range(5) means that it compares the port value between two 
        numbers, so this operator needs 2 operands. One operand is 
        the starting port number of the range which is macIpExternSrcPort1 
        object, and the other operand is the ending port number of the 
        range which the macIpExternDstPort2 object is in.
        
        Now support(3)eq,(5)range."
            ::= { macIpExternAclEntry 18 }

--xxx.100.10.1.3.9.1.19
        macIpExternDstPort1 OBJECT-TYPE
            SYNTAX INTEGER(0..65535)          
            MAX-ACCESS  read-write
            STATUS  current
            DESCRIPTION
                "The source port number of the TCP or UDP protocol. If the
        macIpExternDstOP object in the same row is range(5), this
        object will be the starting port number of the port range.
        This object cannot be configured if macIpExternStatus in the 
        same row is active(1) or macIpExternDstOP in the same row
        is noOperator(0)."
            ::= { macIpExternAclEntry 19 }

--xxx.100.10.1.3.9.1.20       
	macIpExternDstPort2 OBJECT-TYPE
    	   SYNTAX INTEGER(0..65535)
    	   MAX-ACCESS read-write
    	   STATUS current
    	   DESCRIPTION
        	"The source port number of the TCP or UDP protocol. If the
        macIpExternDstOP object in the same row is range(5), this
        object will be the ending port number of the port range.
        This object cannot be configured if numIpExternStatus in the 
        same row is active(1) or macIpExternDstOP in the same row
        is not range(5)."
    		::= { macIpExternAclEntry 20 }

--xxx.100.10.1.3.9.1.21			
  macIpExternPrecedence OBJECT-TYPE
      SYNTAX  INTEGER(0..7)
      MAX-ACCESS read-write
      STATUS  current
      DESCRIPTION
          "The precedence of macIp-Extern-acl  ."
      ::= { macIpExternAclEntry 21 }

--xxx.100.10.1.3.9.1.22
  macIpExternTos OBJECT-TYPE
      SYNTAX  INTEGER(0..15)
      MAX-ACCESS read-write
      STATUS  current
      DESCRIPTION
          "The tos of macIp-Extern-acl  ."
      ::= { macIpExternAclEntry 22 }
            
--xxx.100.10.1.3.9.1.23
        macIpExternStatus OBJECT-TYPE
            SYNTAX  INTEGER
            	    {
            	    	createAndGo(0),
               		  active(1),
               		  destroy(2)
            	    }
            MAX-ACCESS  read-write
            STATUS  current
            DESCRIPTION
                " state of the access-list."
            ::= { macIpExternAclEntry 23 } 

--xxx.100.10.1.3.9.1.24
        macIpExternVlanId OBJECT-TYPE
    	   SYNTAX INTEGER(1..4094)
    	   MAX-ACCESS read-write
    	   STATUS current
    	   DESCRIPTION
        	"The vlan Id"
    		::= { macIpExternAclEntry 24 }

--xxx.100.10.1.3.9.1.25
        macIpExternVlanIdWild OBJECT-TYPE
    	   SYNTAX INTEGER(0..4095)
    	   MAX-ACCESS read-write
    	   STATUS current
    	   DESCRIPTION
        	"The vlan Id mask"
            ::= { macIpExternAclEntry 25 } 
--********************************************************************************************************
--xxx.100.10.1.4.1
aclActiveTable OBJECT-TYPE
    SYNTAX  SEQUENCE OF AclActiveEntry
    MAX-ACCESS  not-accessible
    STATUS  current
            DESCRIPTION
                "bind  Acl in port or vlan."
            ::= { aclAttach 1  } 
            
--xxx.100.10.1.4.1.1
    aclActiveEntry OBJECT-TYPE
        SYNTAX  AclActiveEntry
        MAX-ACCESS  not-accessible
        STATUS  current
        DESCRIPTION
            "Entry for aclActiveTable"
        INDEX   { aclActiveBindType,aclActiveIndex,aclActiveType, aclActiveDirection }
        ::= { aclActiveTable 1 }

    AclActiveEntry
        ::= SEQUENCE
            {
               aclActiveBindType     INTEGER,
               aclActiveIndex        INTEGER,
               aclActiveType		      INTEGER,
               aclActiveDirection		    INTEGER,                           
               aclActiveAclIndex     INTEGER,                           
               aclActiveStatistic      INTEGER,
               aclActiveStatus         INTEGER
            }
                                                           


--xxx.100.10.1.4.1.1.1
        aclActiveBindType  OBJECT-TYPE
            SYNTAX  INTEGER 
                    {
                      port(0),
                      vlan(1)
                    }
            MAX-ACCESS read-only
            STATUS  current
            DESCRIPTION
                "point out the type of position of the bind-acl."
            ::= { aclActiveEntry 1 }
            
--xxx.100.10.1.4.1.1.2
        aclActiveIndex  OBJECT-TYPE
            SYNTAX  INTEGER 
            MAX-ACCESS read-only
            STATUS  current
            DESCRIPTION
                "The value of port id or vlan id  ."
            ::= { aclActiveEntry 2 }       
                 
--xxx.100.10.1.4.1.1.3
        aclActiveType  OBJECT-TYPE
            SYNTAX  INTEGER
                {
                   ip(1),
                   ipv6(3), 
                   mac(5),
                   macIp(8)
                                 
                }  
            MAX-ACCESS read-only
            STATUS  current
            DESCRIPTION
                "the type of acl."
            ::= { aclActiveEntry 3 }
            
 --xxx.100.10.1.4.1.1.4
        aclActiveDirection  OBJECT-TYPE
            SYNTAX  INTEGER
                {
                   out(0),
                   in(1)
                }  
            MAX-ACCESS read-only
            STATUS  current
            DESCRIPTION
                "the direction of a binding acl."
            ::= { aclActiveEntry 4 }           
            
--xxx.100.10.1.4.1.1.5
        aclActiveAclIndex  OBJECT-TYPE
            SYNTAX  INTEGER 
            MAX-ACCESS read-write
            STATUS  current
            DESCRIPTION
                "the value of acl index,you have configured in aclNumAccessGroupTable or aclNameAccessGroupTable."
            ::= { aclActiveEntry 5 }
                       
 --xxx.100.10.1.4.1.1.6
        aclActiveStatistic  OBJECT-TYPE
            SYNTAX  INTEGER
                {
                   disable(0),
                   enable(1)
                }  
            MAX-ACCESS read-write
            STATUS  current
            DESCRIPTION
                "support traffic statistic or not."
            ::= { aclActiveEntry 6 }   
            
            
 
--xxx.100.10.1.4.1.1.7
        aclActiveStatus  OBJECT-TYPE
            SYNTAX  INTEGER
                {
                   disable(0),
                   enable(1)
                }  
            MAX-ACCESS read-write
            STATUS  current
            DESCRIPTION
                "access or delete the bind-acl."
            ::= { aclActiveEntry 7} 
            
--*********************************************************************************************************
--xxx.100.10.1.4.2
aclStatisticClearTable OBJECT-TYPE
    SYNTAX  SEQUENCE OF AclStatisticClearEntry
    MAX-ACCESS  not-accessible
    STATUS  current
            DESCRIPTION
                "clear traffic-statistic in port or vlan."
            ::= { aclAttach 2  } 
            
--xxx.100.10.1.4.2.1
    aclStatisticClearEntry OBJECT-TYPE
        SYNTAX  AclStatisticClearEntry
        MAX-ACCESS  not-accessible
        STATUS  current
        DESCRIPTION
            "entry for aclStatisticClearTable"
        INDEX   { aclActiveBindType,aclActiveDirection,aclActiveIndex }
        ::= { aclStatisticClearTable 1 }

    AclStatisticClearEntry
        ::= SEQUENCE
            {
               aclStatisticClearBindType     INTEGER,               
               aclStatisticClearDirection		    INTEGER,
               aclStatisticClearIndex        INTEGER,                                                                   
               aclStatisticClearStatus       INTEGER             
            }
                                                           


--xxx.100.10.1.4.2.1.1
        aclStatisticClearBindType  OBJECT-TYPE
            SYNTAX  INTEGER 
                    {
                      port(0),
                      vlan(1)
                    }
            MAX-ACCESS read-only
            STATUS  current
            DESCRIPTION
                "point out the type of position of the bind-acl."
            ::= { aclStatisticClearEntry 1 }
            
 --xxx.100.10.1.4.2.1.2
        aclStatisticClearDirection  OBJECT-TYPE
            SYNTAX  INTEGER
                {
                   out(0),
                   in(1)
                }  
            MAX-ACCESS read-only
            STATUS  current
            DESCRIPTION
                "the direction of a binding acl."
            ::= { aclStatisticClearEntry 2 }
            
--xxx.100.10.1.4.2.1.3
        aclStatisticClearIndex  OBJECT-TYPE
            SYNTAX  INTEGER 
            MAX-ACCESS read-only
            STATUS  current
            DESCRIPTION
                "The value of port id or vlan id   ."
            ::= { aclStatisticClearEntry 3 }
            
--xxx.100.10.1.4.2.1.4
        aclStatisticClearStatus  OBJECT-TYPE
            SYNTAX  INTEGER
                {
                   disable(0),
                   enable(1)
                }  
            MAX-ACCESS read-write
            STATUS  current
            DESCRIPTION
                "clear the bind-acl's traffic-statistic."
            ::= { aclStatisticClearEntry 4}                                            
--******************************************************************************************************** 
--xxx.100.10.2
    sshMgt         	    OBJECT IDENTIFIER ::= { prisecurity 2 } 
    
--******************************************************************************************************** 

sshServerStatus OBJECT-TYPE
        SYNTAX      INTEGER
                    {
               		enable(1),
               		disable(0)
            	    }
        MAX-ACCESS  read-write
        STATUS      current
        DESCRIPTION "The status of Secure Shell Server, set this value
                     to 1 to enable SSH server, set this value to 0 to 
                     disable the SSH server."
        ::= { sshMgt 1 }

sshServerVersion  OBJECT-TYPE
        SYNTAX      INTEGER
        MAX-ACCESS  read-only
        STATUS      current
        DESCRIPTION "The version of the SSH Server."
        ::= { sshMgt 2 }
 
sshTimeout OBJECT-TYPE
        SYNTAX      INTEGER(10..600)
        MAX-ACCESS  read-write
        STATUS      current
        DESCRIPTION "The time interval that the router waits for the SSH 
                     client to respond. The range is 10-600."
        ::= { sshMgt 3 }

sshAuthRetries OBJECT-TYPE
        SYNTAX      INTEGER(1..10)
        MAX-ACCESS  read-write
        STATUS      current
        DESCRIPTION "The number of attempts after which the interface is reset.
                     The range is 1-10."
        ::= { sshMgt 4 }
        
--********************************************************************************************************
 
sshUseTable OBJECT-TYPE
        SYNTAX      SEQUENCE OF SshUseEntry
        MAX-ACCESS  not-accessible
        STATUS      current
        DESCRIPTION "The table for Secure Shell Connection."
        ::= { sshMgt 5 }

sshUseEntry OBJECT-TYPE
        SYNTAX      SshUseEntry
        MAX-ACCESS  not-accessible
        STATUS      current
        DESCRIPTION "The conceptual row for sshConnInfoTable."
        INDEX       { sshUserIndex }
        ::= { sshUseTable 1 }

SshUseEntry ::= SEQUENCE
{
   sshUserIndex		   INTEGER,
   sshUserName             DisplayString,   
   sshUserType   	   INTEGER,
   sshUserPassword         DisplayString,  
   sshUserStatus   	   INTEGER 
}

sshUserIndex OBJECT-TYPE
        SYNTAX      INTEGER
        MAX-ACCESS  not-accessible
        STATUS      current
        DESCRIPTION ""
        ::= { sshUseEntry 1 }
        
sshUserName OBJECT-TYPE
        SYNTAX      DisplayString(SIZE(1..16))
        MAX-ACCESS  read-write
        STATUS      current
        DESCRIPTION ""
        ::= { sshUseEntry 2 }
        
sshUserType OBJECT-TYPE
        SYNTAX      INTEGER
        	{
            	    	noCryptograph(0),
               		cryptograph(7)      	
        	}
        MAX-ACCESS  read-write
        STATUS      current
        DESCRIPTION ""
        ::= { sshUseEntry 3 }        
        
sshUserPassword OBJECT-TYPE
        SYNTAX      DisplayString(SIZE(1..32))
        MAX-ACCESS  read-write
        STATUS      current
        DESCRIPTION ""
        ::= { sshUseEntry 4 }
        
sshUserStatus OBJECT-TYPE
        SYNTAX      INTEGER
        	{
            	    	createAndGo(0),
               		active(1),
               		destroy(2)    	
        	}
        MAX-ACCESS  read-write
        STATUS      current
        DESCRIPTION ""
        ::= { sshUseEntry 5 }          
          
--******************************************************************************************************** 

sshConnInfoTable OBJECT-TYPE
        SYNTAX      SEQUENCE OF SshConnInfoEntry
        MAX-ACCESS  not-accessible
        STATUS      current
        DESCRIPTION "The table for Secure Shell Connection."
        ::= { sshMgt 6 }

sshConnInfoEntry OBJECT-TYPE
        SYNTAX      SshConnInfoEntry
        MAX-ACCESS  not-accessible
        STATUS      current
        DESCRIPTION "The conceptual row for sshConnInfoTable."
        INDEX       { sshConnID }
        ::= { sshConnInfoTable 1 }

SshConnInfoEntry ::= SEQUENCE
{
   sshConnID             INTEGER,
   sshConnVersion   	 INTEGER,
   sshConnStatus         INTEGER,   
   sshConnUserName       DisplayString 
}

sshConnID OBJECT-TYPE
        SYNTAX      INTEGER
        MAX-ACCESS  read-only
        STATUS      current
        DESCRIPTION "The connection ID of the Secure Shell Connection."
        ::= { sshConnInfoEntry 1 }

sshConnVersion OBJECT-TYPE
        SYNTAX      INTEGER
        MAX-ACCESS  read-only
        STATUS      current
        DESCRIPTION "The SSH version."
        ::= { sshConnInfoEntry 2 }

sshConnStatus OBJECT-TYPE
        SYNTAX      INTEGER
                    {
                      negotiationStart(1),
                      authenticationStart(2),
                      sessionStart(3)
                    } 
        MAX-ACCESS  read-only
        STATUS      current
        DESCRIPTION "The SSH connection State. negotiationStart(1) mean the
                     SSH is in its negotiation start state, authenticationStart(2)
                     mean the SSH is in authentication start state, sessionStart(3)
                     mean the SSH is in session start State."
        ::= { sshConnInfoEntry 3 }
        
sshConnUserName OBJECT-TYPE
        SYNTAX      DisplayString
        MAX-ACCESS  read-only
        STATUS      current
        DESCRIPTION "User Name."
        ::= { sshConnInfoEntry 4 }        
        
        
        
--********************************************************************************************************
--********************************************************************************************************  
-- Management for Terminal Access Controller Access Control System plus (TACACS+).

--xxx.100.10.3
    tacacsMgt         	    OBJECT IDENTIFIER ::= { prisecurity 3 } 
    
--********************************************************************************************************         

tacacsServerHostTable OBJECT-TYPE
        SYNTAX      SEQUENCE OF TacacsServerHostEntry
        MAX-ACCESS  not-accessible
        STATUS      current
        DESCRIPTION "IP address of TACACS server."
        ::= { tacacsMgt 1 }

tacacsServerHostEntry OBJECT-TYPE
        SYNTAX  TacacsServerHostEntry
        MAX-ACCESS  not-accessible
        STATUS  current
        DESCRIPTION
            ""
        INDEX   { tacacsServerHostIndex }
        ::= { tacacsServerHostTable 1 } 

    TacacsServerHostEntry
        ::= SEQUENCE
            {
            	tacacsServerHostIndex		INTEGER,
                tacacsServerHostIP		IpAddress,
                tacacsServerHostPort		INTEGER,	                
                tacacsServerHostPrimary		INTEGER,
                tacacsServerHostStatus		INTEGER,  
                tacacsServerHostKey		DisplayString,
                tacacsServerHostTimeout		INTEGER                    
            }
            
tacacsServerHostIndex OBJECT-TYPE
        SYNTAX      INTEGER
        MAX-ACCESS  not-accessible
        STATUS      current
        DESCRIPTION "IP address of TACACS server."
        ::= { tacacsServerHostEntry 1 }

tacacsServerHostIP OBJECT-TYPE
        SYNTAX      IpAddress
        MAX-ACCESS  read-write
        STATUS      current
        DESCRIPTION "IP address of TACACS server."
        ::= { tacacsServerHostEntry 2 }
        
tacacsServerHostPort OBJECT-TYPE
        SYNTAX      INTEGER(0..65535)
        MAX-ACCESS  read-write
        STATUS      current
        DESCRIPTION "Port of TACACS server."
        ::= { tacacsServerHostEntry 3 }        
        
tacacsServerHostPrimary OBJECT-TYPE
        SYNTAX      INTEGER
                    {
            	    	noPrimary(0),
               		primary(1)
                    }          
        MAX-ACCESS  read-write
        STATUS      current
        DESCRIPTION ""
        ::= { tacacsServerHostEntry 4 }          

tacacsServerHostStatus OBJECT-TYPE
        SYNTAX      INTEGER
                    {
            	    	createAndGo(0),
               		active(1),
               		destroy(2)
                    }  
        MAX-ACCESS  read-write
        STATUS      current
        DESCRIPTION ""
        ::= { tacacsServerHostEntry 5 }
        
tacacsServerHostKey OBJECT-TYPE
        SYNTAX      DisplayString (SIZE(1..16))
        MAX-ACCESS  read-write
        STATUS      current
        DESCRIPTION "Key for TACACS. Input space(' ') to clear this key"
        ::= { tacacsServerHostEntry 6 }          
        
tacacsServerHostTimeout OBJECT-TYPE
        SYNTAX      INTEGER (0..60)
        MAX-ACCESS  read-write
        STATUS      current
        DESCRIPTION "The time before retransmit of the TACACS server."
        ::= { tacacsServerHostEntry 7 }          
         
--********************************************************************************************************

tacacsServerTimeout OBJECT-TYPE
        SYNTAX      INTEGER (1..60)
        MAX-ACCESS  read-write
        STATUS      current
        DESCRIPTION "The time before retransmit of the TACACS server."
        ::= { tacacsMgt 2 }

tacacsServerKey OBJECT-TYPE
        SYNTAX      DisplayString (SIZE(1..16))
        MAX-ACCESS  read-write
        STATUS      current
        DESCRIPTION "Key for TACACS. Input space(' ') to clear this key"
        ::= { tacacsMgt 3 }
        
--********************************************************************************************************
--********************************************************************************************************  

--xxx.100.10.4
    am         	    OBJECT IDENTIFIER ::= { prisecurity 4 } 
    
--********************************************************************************************************         

amGlobalEnable OBJECT-TYPE
        SYNTAX  INTEGER {
                enable (1),
                disable (2)
            }
        MAX-ACCESS  read-write
        STATUS      current
        DESCRIPTION " Global Enable or disable the Access Management."
        ::= { am 1 }

--********************************************************************************************************
      
amPortInfoTable OBJECT-TYPE
        SYNTAX      SEQUENCE OF AmPortInfoEntry
        MAX-ACCESS  not-accessible
        STATUS      current
        DESCRIPTION "Access Management information list of port."
        ::= { am 2 }

amPortInfoEntry OBJECT-TYPE
        SYNTAX  AmPortInfoEntry
        MAX-ACCESS  not-accessible
        STATUS  current
        DESCRIPTION
            ""
        INDEX   { amPortIndex,amPortIp }
        ::= { amPortInfoTable 1 } 

    AmPortInfoEntry
        ::= SEQUENCE
            {
                amPortIndex               		        INTEGER,
                amPortEnable				        INTEGER,
                amPortForwardingType				INTEGER,
                amPortIp					IpAddress,
                amPortMac				        MacAddress,
                amPortCount					INTEGER,
                amPortStatus				        INTEGER        
            }
            
amPortIndex OBJECT-TYPE
        SYNTAX      INTEGER
        MAX-ACCESS  not-accessible
        STATUS      current
        DESCRIPTION "port index"
        ::= { amPortInfoEntry 1 }       
        
amPortEnable OBJECT-TYPE
        SYNTAX  INTEGER {
                enable (1),
                disable (2)
            }
        MAX-ACCESS  read-write
        STATUS      current
        DESCRIPTION "Enable or disable the Access Management on the port."
        ::= { amPortInfoEntry 2 }
                
amPortForwardingType OBJECT-TYPE
        SYNTAX  INTEGER{
			ip-pool(1),
			mac-ip-pool(2)
            }   
        MAX-ACCESS  read-write
        STATUS      current
        DESCRIPTION "Access Management forwarding type."
        ::= { amPortInfoEntry 3 }
 
amPortIp OBJECT-TYPE
        SYNTAX      IpAddress
        MAX-ACCESS  read-only
        STATUS      current
        DESCRIPTION "IP address of Access Management."
        ::= { amPortInfoEntry 4 } 
        
amPortMac OBJECT-TYPE
        SYNTAX      MacAddress         
        MAX-ACCESS  read-write
        STATUS      current
        DESCRIPTION "Mac address of Access Management."
        ::= { amPortInfoEntry 5 }          

amPortCount OBJECT-TYPE
        SYNTAX      INTEGER(1..32)
        MAX-ACCESS  read-write
        STATUS      current
        DESCRIPTION "Seriate IP address number."
        ::= { amPortInfoEntry 6 }  

amPortStatus OBJECT-TYPE
        SYNTAX      INTEGER
                    {
            	    	createAndGo(0),
               		active(1),
               		destroy(2)
                    }  
        MAX-ACCESS  read-write
        STATUS      current
        DESCRIPTION ""
        ::= { amPortInfoEntry 7 }  
         
--********************************************************************************************************
--********************************************************************************************************

--xxx.100.10.5
    radiusMgt         	    OBJECT IDENTIFIER ::= { prisecurity 5 } 
    
--********************************************************************************************************         

aaaEnabled          OBJECT-TYPE
        SYNTAX      INTEGER 
                     {
            	    	enable(1),
               		  disable(0)
                    }        
        MAX-ACCESS  read-write
        STATUS      current
        DESCRIPTION "Enable or disable Aaa function."
        ::= { radiusMgt  1 }
        
aaaAccount          OBJECT-TYPE
        SYNTAX      INTEGER 
                     {
            	    	enable(1),
               		  disable(0)
                    }        
        MAX-ACCESS  read-write
        STATUS      current
        DESCRIPTION "Enable or disable Aaa Accounting function."
        ::= { radiusMgt  2 }        
        
aaaAccountUpdate    OBJECT-TYPE
        SYNTAX      INTEGER 
                     {
            	    	enable(1),
               		  disable(0)
                    }        
        MAX-ACCESS  read-write
        STATUS      current
        DESCRIPTION "Enable or disable Aaa Accounting update function."
        ::= { radiusMgt  3 }  
        
aaaAccountBindingDHCP    OBJECT-TYPE
        SYNTAX      INTEGER 
                     {
            	    	enable(1),
               		  disable(0)
                    }        
        MAX-ACCESS  read-write
        STATUS      current
        DESCRIPTION "Enable or disable Aaa Accounting DHCP-Binding function."
        ::= { radiusMgt  4 }   
          
--********************************************************************************************************   
       
radiusAuthenServerHostTable OBJECT-TYPE
        SYNTAX      SEQUENCE OF RadiusAuthenServerHostEntry
        MAX-ACCESS  not-accessible
        STATUS      current
        DESCRIPTION "Configuration items and information list of RADIUS authentication server host."
        ::= { radiusMgt  5 }

radiusAuthenServerHostEntry OBJECT-TYPE
        SYNTAX  RadiusAuthenServerHostEntry
        MAX-ACCESS  not-accessible
        STATUS  current
        DESCRIPTION  ""
        INDEX   { radiusAuthenServerHostIndex }
        ::= { radiusAuthenServerHostTable 1 } 

       RadiusAuthenServerHostEntry
        ::= SEQUENCE
            {
            	  radiusAuthenServerHostIndex		INTEGER,
                radiusAuthenServerHostIP		DisplayString,
                radiusAuthenServerHostPort		INTEGER,
                radiusAutServerHostKey		DisplayString, 
                radiusAuthenServerHostPrimary	INTEGER,
                radiusAutServerHostAccessMode   INTEGER,
                radiusAuthenServerHostStatus		INTEGER          
            }
            
radiusAuthenServerHostIndex OBJECT-TYPE
        SYNTAX      INTEGER
        MAX-ACCESS  not-accessible
        STATUS      current
        DESCRIPTION "Index of RADIUS authentication server."
        ::= { radiusAuthenServerHostEntry 1 }      
        
radiusAuthenServerHostIP OBJECT-TYPE
        SYNTAX      DisplayString (SIZE(1..39))
        MAX-ACCESS  read-write
        STATUS      current
        DESCRIPTION "IP address of RADIUS authentication server."
        ::= { radiusAuthenServerHostEntry 2 }
        
radiusAuthenServerHostPort OBJECT-TYPE
        SYNTAX      INTEGER(0..65535)
        MAX-ACCESS  read-write
        STATUS      current
        DESCRIPTION "Port of RADIUS authentication server."
        ::= { radiusAuthenServerHostEntry 3 }        
        
radiusAutServerHostKey OBJECT-TYPE
        SYNTAX      DisplayString (SIZE(1..64))
        MAX-ACCESS  read-write
        STATUS      current
        DESCRIPTION "Key for RADIUS authentication server. Input space(' ') to clear this key"
        ::= { radiusAuthenServerHostEntry 4 }
        
radiusAuthenServerHostPrimary OBJECT-TYPE
        SYNTAX      INTEGER
                    {
            	    	noPrimary(0),
               		  primary(1)
                    }          
        MAX-ACCESS  read-write
        STATUS      current
        DESCRIPTION "Configuration of primary or not primary "
        ::= { radiusAuthenServerHostEntry 5 } 
        
radiusAutServerHostAccessMode OBJECT-TYPE
        SYNTAX      INTEGER
                    {
                    none(0),
            	    	dot1x(1),
               		  telnet(2)
                    }          
        MAX-ACCESS  read-write
        STATUS      current
        DESCRIPTION "Configuration access mode of none, dot1x or telnet "
        ::= { radiusAuthenServerHostEntry 6 }          

radiusAuthenServerHostStatus OBJECT-TYPE
        SYNTAX      INTEGER
                    {            	    
               		active(1),
               		destroy(2)
                    }  
        MAX-ACCESS  read-write
        STATUS      current
        DESCRIPTION "Setting it to  active(1) to creates an entry,setting it to destroy(2) to destroy an entry."
        ::= { radiusAuthenServerHostEntry 7 }   
        
--********************************************************************************************************  
        
radiusAcctServerHostTable OBJECT-TYPE
        SYNTAX      SEQUENCE OF RadiusAcctServerHostEntry
        MAX-ACCESS  not-accessible
        STATUS      current
        DESCRIPTION "Configuration items and information list of RADIUS accounting server host."
        ::= { radiusMgt  6 }

radiusAcctServerHostEntry OBJECT-TYPE
        SYNTAX RadiusAcctServerHostEntry
        MAX-ACCESS  not-accessible
        STATUS  current
        DESCRIPTION  ""
        INDEX   { radiusAcctServerHostIndex }
        ::= { radiusAcctServerHostTable 1 } 

      RadiusAcctServerHostEntry
        ::= SEQUENCE
            {
            	  radiusAcctServerHostIndex		INTEGER,
                radiusAcctServerHostIP		DisplayString,
                radiusAcctServerHostPort		INTEGER,	                
                radiusAcctServerHostKey		DisplayString, 
                radiusAcctServerHostPrimary	INTEGER,
                radiusAcctServerHostStatus		INTEGER          
            }
            
radiusAcctServerHostIndex  OBJECT-TYPE
        SYNTAX      INTEGER
        MAX-ACCESS  not-accessible
        STATUS      current
        DESCRIPTION "Index of RADIUS accounting server."
        ::= { radiusAcctServerHostEntry 1 }      
        
radiusAcctServerHostIP OBJECT-TYPE
        SYNTAX      DisplayString (SIZE(1..39))
        MAX-ACCESS  read-write
        STATUS      current
        DESCRIPTION "IP address of RADIUS accounting server."
        ::= { radiusAcctServerHostEntry 2 }
        
radiusAcctServerHostPort OBJECT-TYPE
        SYNTAX      INTEGER(0..65535)
        MAX-ACCESS  read-write
        STATUS      current
        DESCRIPTION "Port of RADIUS accounting server."
        ::= { radiusAcctServerHostEntry 3 }        
        
radiusAcctServerHostKey OBJECT-TYPE
        SYNTAX      DisplayString (SIZE(1..64))
        MAX-ACCESS  read-write
        STATUS      current
        DESCRIPTION "Key for RADIUS accounting server. Input space(' ') to clear this key"
        ::= { radiusAcctServerHostEntry 4 }

radiusAcctServerHostPrimary	 OBJECT-TYPE
        SYNTAX      INTEGER
                    {
            	    	noPrimary(0),
               		  primary(1)
                    }          
        MAX-ACCESS  read-write
        STATUS      current
        DESCRIPTION "Configuration of primary or not primary "
        ::= { radiusAcctServerHostEntry 5 }          

radiusAcctServerHostStatus OBJECT-TYPE
        SYNTAX      INTEGER
                    {            	    
               		active(1),
               		destroy(2)
                    }  
        MAX-ACCESS  read-write
        STATUS      current
        DESCRIPTION "Setting it to  active(1) to creates an entry,setting it to destroy(2) to destroy an entry."
        ::= { radiusAcctServerHostEntry 6 }       
                                  
--********************************************************************************************************  
radiusServerTimeout OBJECT-TYPE
        SYNTAX      INTEGER (1..1000)
        MAX-ACCESS  read-write
        STATUS      current
        DESCRIPTION "The time before retransmit of the RADIUS server."
        ::= { radiusMgt  7 }
        
radiusServerRetransmit OBJECT-TYPE
        SYNTAX      INTEGER (0..100)
        MAX-ACCESS  read-write
        STATUS      current
        DESCRIPTION "Retransmit time before giving up the current RADIUS server."
        ::= { radiusMgt  8 }
        
radiusServerDeadTime    OBJECT-TYPE
        SYNTAX      INTEGER (1..255)
        MAX-ACCESS  read-write
        STATUS      current
        DESCRIPTION "The time before retry of the down-server."
        ::= { radiusMgt  9 }
         
radiusServerKey OBJECT-TYPE
        SYNTAX      DisplayString (SIZE(1..64))
        MAX-ACCESS  read-write
        STATUS      current
        DESCRIPTION "Key for RADIUS. Input space(' ') to clear this key"
        ::= { radiusMgt  10 }
    
radiusServerAccountTimeOut   OBJECT-TYPE
        SYNTAX      INTEGER (60..3600)
        MAX-ACCESS  read-write
        STATUS      current
        DESCRIPTION "Accounting update interval."
        ::= { radiusMgt  11 } 
radiusServerNasIpv4   OBJECT-TYPE
        SYNTAX      IpAddress
        MAX-ACCESS  read-write
        STATUS      current
        DESCRIPTION "Radius server nas IPv4. Input 0.0.0.0 to delete nas ipv4 address"
        ::= { radiusMgt  12 } 
radiusServerNasIpv6   OBJECT-TYPE
        SYNTAX      DisplayString (SIZE(1..39))
        MAX-ACCESS  read-write
        STATUS      current
        DESCRIPTION "Radius server nas IPv6. Input 0 to delete nas IPv6 address"
        ::= { radiusMgt  13 }         
--********************************************************************************************************
-- (xxx.100.11)   priQos group               

--xxx.100.11.1
    qos         	    OBJECT IDENTIFIER ::= { priQos 1 } 

--******************************************************************************************************** 
    
--xxx.100.11.1.1
qosEnable OBJECT-TYPE
    SYNTAX  INTEGER{
                disable(0),
                enable(1)
            }
            MAX-ACCESS  read-write
            STATUS  current
            DESCRIPTION
                "qos golbal switch.disable express close,enable is open."
            ::= { qos 1 } 
            
--********************************************************************************************************

--xxx.100.11.1.2
qosPortTable OBJECT-TYPE
    SYNTAX  SEQUENCE OF QosPortEntry
    MAX-ACCESS  not-accessible
    STATUS  current
            DESCRIPTION
                "qos port configration."
            ::= { qos 2 } 

--xxx.100.11.1.2.1
    qosPortEntry OBJECT-TYPE
        SYNTAX  QosPortEntry
        MAX-ACCESS  not-accessible
        STATUS  current
        DESCRIPTION
            " qos port list of concrete definition.index is port index"
        INDEX   { qosPortIndex }
        ::= { qosPortTable 1 } 

    QosPortEntry
        ::= SEQUENCE
            {
                qosPortIndex			INTEGER,
                qosPortType			INTEGER,	                
                qosPortCos			INTEGER,
		qosPortTrust			INTEGER,
		qosPortPriority			INTEGER,
		qosPortMutation			DisplayString,
		qosPortQueue			INTEGER,
                qosPortStatus		       	INTEGER          
            }

--xxx.100.11.1.2.1.1
qosPortIndex OBJECT-TYPE
    SYNTAX  INTEGER
            MAX-ACCESS  not-accessible
            STATUS  current
            DESCRIPTION
                "port Index"
            ::= { qosPortEntry 1 } 

--xxx.100.11.1.2.1.2
qosPortType OBJECT-TYPE
    SYNTAX  INTEGER
                {
            		  cos(1),
            	    trust(0),
               		dscpMutation(2),
               		priorityQueueOut(3)	
            	}
            MAX-ACCESS  read-create
            STATUS  current
            DESCRIPTION
                "the relation between qosPortType and CLI:
                1 mls qos cos {<default-cos> };     
		0 mls qos trust {cos [pass-through-cos] [pass-through-dscp]|dscp [pass-through-cos] [pass-through-dscp]| ip-precedence [pass-through-cos] [pass-through-dscp] |port priority <cos> [pass-through-cos] [pass-through-dscp]} ;
		2 mls qos dscp-mutation <dscp-mutation-name>;
		3 priority-queue out.
		According to the relation,when configurate qos with snmp,first set the qosPortType to the correct value to select CLI,
		then set next CLI parameter.Fox example,set qos default cos is 5, first set qosPortType=1 ,then set qosPortCos to 5,
		finally setting qosPortStatus to 1, trigger snmp-cache works."
            ::= { qosPortEntry 2 } 
                               
--xxx.100.11.1.2.1.3
qosPortCos OBJECT-TYPE
    SYNTAX  INTEGER(0..7)
            MAX-ACCESS  read-create
            STATUS  current
            DESCRIPTION
                "port default cos value"
            ::= { qosPortEntry 3 } 

--xxx.100.11.1.2.1.4
qosPortTrust OBJECT-TYPE
    SYNTAX  INTEGER
            	{
            		  priority(0),
            	    priAndPassThroughDscp(1),
            	    priAndPassThroughCos(2),
               		priAndPassThroughCosAndPassThroughDscp(3),
               		cos(4),
               		cosAndPassThroughDscp(5),
               		cosAndPassThroughCos(6),
               		cosAndPassThroughCosAndPassThroughDscp(7),
               		dscp(8),
               		dscpAndPassThroughCos(9),
               		dscpAndPassThroughDscp(10),
               		dscpAndPassThroughDscpAndPassThroughCos(11),
               		ipPrecedence(12),
               		ipPreAndPassThroughCos(13),
               		ipPreAndPassThroughDSCP(14),
               		ipPreAndPassThroughDSCPAndPassThroughCos(15),
               		mplsEXP(16)
            	}
            MAX-ACCESS  read-create
            STATUS  current
            DESCRIPTION
                "Configure port trust.
                  priority(0),mls qos trust port priority <cos>;
                  priAndPassThroughDscp(1),opposite cli is mls qos trust port priority <cos> pass-through-dscp;
                  priAndPassThroughCos(2),opposite cli is mls qos trust port priority <cos> pass-through-cos;
                  priAndPassThroughCosAndPassThroughDscp(3),opposite cli is mls qos trust port priority <cos> pass-through-cos pass-through-dscp;
            	    cos(4),mls qos trust cos;
               	  cosAndPassThroughDscp(5),opposite cli is mls qos trust cos pass-through-dscp;
               	  cosAndPassThroughCos(6),opposite cli is mls qos trust cos pass-through-cos;
               	  cosAndPassThroughCosAndPassThroughDscp(7),opposite cli is mls qos trust cos pass-through-cos pass-through-dscp;
               	  dscp(8),mls qos trust dscp;
               	  dscpAndPassThroughCos(9),opposite cli is mls qos trust dscp pass-through-cos;
               	  dscpAndPassThroughDscp(10),opposite cli is mls qos trust dscp pass-through-dscp;
               	  dscpAndPassThroughDscpAndPassThroughCos(11),opposite cli is mls qos trust dscp pass-through-dscp pass-through-cos;
               	  ipPrecedence(12), mls qos trust ip-precedence;
               	  ipPreAndPassThroughCos(13),opposite cli is mls qos trust ip-precedence pass-through-cos;
               	  ipPreAndPassThroughDSCP(14),opposite cli is mls qos trust ip-precedence pass-through-dscp;
               	  ipPreAndPassThroughDSCPAndPassThroughCos(15),opposite cli is mls qos trust ip-precedence pass-through-dscp pass-through-cos;
               	  mplsEXP(16),mls qos mpls trust exp."
            ::= { qosPortEntry 4 } 
            
--xxx.100.11.1.2.1.5
qosPortPriority OBJECT-TYPE
    SYNTAX  INTEGER (0..7)
            MAX-ACCESS  read-create
            STATUS  current
            DESCRIPTION
                "The corresponding CLI:mls qos trust port priority <cos>."
            ::= { qosPortEntry 5 }             

--xxx.100.11.1.2.1.6
qosPortMutation OBJECT-TYPE
    SYNTAX  DisplayString
            MAX-ACCESS  read-create
            STATUS  current
            DESCRIPTION
                "configure port of dscp-mutation,opposite cli 'mls qos dscp-mutation <dscp-mutation-name>'"
            ::= { qosPortEntry 6 }  

--xxx.100.11.1.2.1.7
        qosPortQueue OBJECT-TYPE
            SYNTAX  INTEGER
            	    {
            	    	priorityQueue(0),
               		wrrQueue(1)
            	    }
            MAX-ACCESS  read-create
            STATUS  current
            DESCRIPTION
                "priorityQueue configure queue out method to strict priority-queue method;
                 wrrQueue restores the default wrr queue out method."
            ::= { qosPortEntry 7 } 

--xxx.100.11.1.2.1.8
        qosPortStatus OBJECT-TYPE
            SYNTAX  INTEGER
            	    {
               		active(1),
               		destroy(2)
            	    }
            MAX-ACCESS  read-create
            STATUS  current
            DESCRIPTION
                " Setting it to  active(1) to creates an entry,setting it to destroy(2) to destroy an entry."
            ::= { qosPortEntry 8 } 

--******************************************************************************************************** 

--xxx.100.11.1.3
qosClassMapTable OBJECT-TYPE
    SYNTAX  SEQUENCE OF QosClassMapEntry
    MAX-ACCESS  not-accessible
    STATUS  current
            DESCRIPTION
                "classmap configure list"
            ::= { qos 3 } 

--xxx.100.11.1.3.1
    qosClassMapEntry OBJECT-TYPE
        SYNTAX  QosClassMapEntry
        MAX-ACCESS  not-accessible
        STATUS  current
        DESCRIPTION
            " about classmap list of concrete definition,index is classmapname."
        INDEX   { qosClassMapName }
        ::= { qosClassMapTable 1 }
        
    QosClassMapEntry
        ::= SEQUENCE
            {
                qosClassMapName			DisplayString,                
                qosClassMapType			INTEGER,
                qosClassMapAccessGroup       		DisplayString,
                qosClassMapDscp			DisplayString,
                qosClassMapV6Dscp			DisplayString,
                qosClassMapIpPre			DisplayString,
                qosClassMapV6AccGroup		DisplayString,
                qosClassMapV6Flow			DisplayString,
                qosClassMapVlan   			DisplayString,
                qosClassCos   			DisplayString,
                qosClassMapEXPtopmost      DisplayString,
                qosClassMapStatus		       	INTEGER          
            }

--xxx.100.11.1.3.1.1
        qosClassMapName OBJECT-TYPE
            SYNTAX  DisplayString (SIZE(1..32))
            MAX-ACCESS  not-accessible
            STATUS  current
            DESCRIPTION
                "classmap name"
            ::= { qosClassMapEntry 1}

--xxx.100.11.1.3.1.2
        qosClassMapType OBJECT-TYPE
            SYNTAX  INTEGER
            	{
            	    configurClassMap(0),
            	    accessGroup(1),
               		dscp(2),
               		v6dscp(5),
               		ippre(3),
               		v6AccessGroup(8),
               		v6Flow(7),
               		vlan(4), 
               		cos(9),
               		exptopmost(10)
            	}
            MAX-ACCESS  read-create
            STATUS  current
            DESCRIPTION
                "0 class-map <class-map-name>,index is classmapname;
		1 match access-group <acl-index-or-name>,need qosClassMapAccessGroup cooperation;
		2 match ip dscp <dscp-list>    qosClassMapDscp ;
		3 match ip precedence <ip-precedence-list>  qosClassMapIpPre;
		4 match vlan <vlan-list>     qosClassMapVlan;
		5 match ipv6 dscp <dscp-list>    qosClassMapV6Dscp;
		7 match ipv6 flowlabel      qosClassMapV6Flow;
		8 match ipv6 access-group     qosClassMapV6AccGroup
		9 match cos     qosClassCos
	  10 match mpls-experimental topmost    qosClassMapEXPtopmost"
            ::= { qosClassMapEntry  2 }

--xxx.100.11.1.3.1.3
        qosClassMapAccessGroup OBJECT-TYPE
            SYNTAX  DisplayString
            MAX-ACCESS  read-create
            STATUS  current
            DESCRIPTION
                "Match specify access-group (name or number). 
                This object be configured only if qosClassMapType  
                in the same row is accessGroup(1)."
            ::= { qosClassMapEntry  3 }
            
--xxx.100.11.1.3.1.4
        qosClassMapDscp OBJECT-TYPE
            SYNTAX  DisplayString
            MAX-ACCESS  read-create
            STATUS  current
            DESCRIPTION
                "Match specify Dscp.
                This object be configured only if qosClassMapType 
                in the same row is dscp(2)."
            ::= { qosClassMapEntry  4 }  
                      
--xxx.100.11.1.3.1.5
        qosClassMapV6Dscp OBJECT-TYPE
            SYNTAX  DisplayString
            MAX-ACCESS  read-create
            STATUS  current
            DESCRIPTION
                "Match specify ipv6 Dscp.
                This object be configured only if qosClassMapType 
                in the same row is v6dscp(5)."
            ::= { qosClassMapEntry  5 } 
            
--xxx.100.11.1.3.1.6
        qosClassMapIpPre OBJECT-TYPE
            SYNTAX  DisplayString
            MAX-ACCESS  read-create
            STATUS  current
            DESCRIPTION
                "Match specify Ip Precedence.
                This object be configured only if qosClassMapType 
                in the same row is ippre(3)."
            ::= { qosClassMapEntry  6 } 
            
--xxx.100.11.1.3.1.7
        qosClassMapV6AccGroup OBJECT-TYPE
            SYNTAX  DisplayString
            MAX-ACCESS  read-create
            STATUS  current
            DESCRIPTION
                "Match specify Ipv6 Access-Group.
                This object be configured only if qosClassMapType  
                in the same row is v6AccessGroup(8)."
            ::= { qosClassMapEntry  7 } 
            
--xxx.100.11.1.3.1.8
        qosClassMapV6Flow OBJECT-TYPE
            SYNTAX  DisplayString
            MAX-ACCESS  read-create
            STATUS  current
            DESCRIPTION
                "Match specify Ipv6 Flowlabel.
                This object be configured only if qosClassMapType  
                in the same row is v6Flow(6)."
            ::= { qosClassMapEntry  8 } 
            
--xxx.100.11.1.3.1.9
        qosClassMapVlan OBJECT-TYPE
            SYNTAX  DisplayString
            MAX-ACCESS  read-create
            STATUS  current
            DESCRIPTION
                "Match specify Vlan list . At most 8 vlan id.
                This object be configured only if qosClassMapType  
                in the same row is vlan(4)."
            ::= { qosClassMapEntry  9 } 
     
--xxx.100.11.1.3.1.10
        qosClassCos OBJECT-TYPE
            SYNTAX  DisplayString
            MAX-ACCESS  read-create
            STATUS  current
            DESCRIPTION
                "Match specify Cos .
                This object be configured only if qosClassMapType  
                in the same row is cos(9)."
            ::= { qosClassMapEntry 10 }

--xxx.100.11.1.3.1.11
	        qosClassMapEXPtopmost  OBJECT-TYPE
	            SYNTAX  DisplayString
	            MAX-ACCESS  read-create
	            STATUS  current
	            DESCRIPTION
	                "Match specify MPLS EXP.
	                This object be configured only if qosClassMapType  
	                in the same row is EXPtopmost(10)."
	            ::= { qosClassMapEntry 11 }  	        
               
--xxx.100.11.1.3.1.12
        qosClassMapStatus OBJECT-TYPE
            SYNTAX  INTEGER
            	    {
               		active(1),
               		destroy(2)
            	    }
            MAX-ACCESS  read-create
            STATUS  current
            DESCRIPTION
                " Setting it to  active(1) to creates an entry,setting it to destroy(2) to destroy an entry."
            ::= { qosClassMapEntry 12 }             
                                            
--********************************************************************************************************

--xxx.100.11.1.4
qosPolicyTable OBJECT-TYPE
    SYNTAX  SEQUENCE OF QosPolicyEntry
    MAX-ACCESS  not-accessible
    STATUS  current
            DESCRIPTION
                "qos policy list"
            ::= { qos 4 } 

--xxx.100.11.1.4.1
    qosPolicyEntry OBJECT-TYPE
        SYNTAX  QosPolicyEntry
        MAX-ACCESS  not-accessible
        STATUS  current
        DESCRIPTION
            " qos policy list of definition,index is qos policy and classmap of name"
        INDEX   { qosPolicyName}
        ::= { qosPolicyTable 1 }
        
    QosPolicyEntry
        ::= SEQUENCE
            {
                qosPolicyName				DisplayString,
                qosPolicyClassMap			DisplayString,
                qosPolicyType				INTEGER,
                qosPolicyRateKbps			INTEGER,
                qosPolicyNormalBurstKbps		INTEGER,
                qosPolicyMaximumBurstKbps 		INTEGER,
                qosPolicyPeakKbps			INTEGER, 
                qosPolicyConformAction		INTEGER,
                qosPolicyConformActionChangeValue	INTEGER,
                qosPolicyExceedAction 		INTEGER,
                qosPolicyViolateAction 		INTEGER, 
                qosPolicyAggregatePolicer		DisplayString,
                qosPolicyStatus				INTEGER                               
            }

--xxx.100.11.1.4.1.1
        qosPolicyName OBJECT-TYPE
            SYNTAX  DisplayString (SIZE(1..32))
            MAX-ACCESS  not-accessible
            STATUS  current
            DESCRIPTION
                "QoS Policy name"
            ::= { qosPolicyEntry 1 }

--xxx.100.11.1.4.1.2
        qosPolicyClassMap OBJECT-TYPE
            SYNTAX  DisplayString (SIZE(1..32))
            MAX-ACCESS  read-create
            STATUS  current
            DESCRIPTION
                "Specify the classmap name.After a policy map is created, it can be associated to a class.
                So, if you want the class map to match the policy map,please setting the qosPolicyType to 1,and then
                setting the qosPolicyStatus to 1 ."
            ::= { qosPolicyEntry 2 }

--xxx.100.11.1.4.1.3
        qosPolicyType OBJECT-TYPE
            SYNTAX  INTEGER            	
            	{
            	    	policymap(0),
            	    	matchclassmap(1),
            	    	sp(2),
               		aggregatePolicer(3)         	
            	}
            MAX-ACCESS  read-create
            STATUS  current
            DESCRIPTION
                "the relation between qosPolicyType and CLI:
		0  policy-map <policy-map-name>;
		1  class <class-map-name>;
		2  police <rate-kbps> <burst-kbyte> [exceed-action {drop | policed-dscp-transmit}];
		3  police aggregate <aggregate-policer-name>; "
            ::= { qosPolicyEntry 3 }
            
--xxx.100.11.1.4.1.4
        qosPolicyRateKbps OBJECT-TYPE
            SYNTAX  INTEGER(1..10000000)
            MAX-ACCESS  read-create
            STATUS  current
            DESCRIPTION
                "Rate Bandwidth of one policymap.
                This object be configured only if qosPolicyType 
                in the same row is sp(2). "
            ::= { qosPolicyEntry 4 }            

--xxx.100.11.1.4.1.5
        qosPolicyNormalBurstKbps OBJECT-TYPE
            SYNTAX  INTEGER(1..1000000)
            MAX-ACCESS  read-create
            STATUS  current
            DESCRIPTION
                "Normal burst kbytes."
            ::= { qosPolicyEntry 5 }
            
--xxx.100.11.1.4.1.6
        qosPolicyMaximumBurstKbps OBJECT-TYPE
            SYNTAX  INTEGER(1..1000000)
            MAX-ACCESS  read-create
            STATUS  current
            DESCRIPTION
                "Maximum burst kbytes."
            ::= { qosPolicyEntry 6 }
            
--xxx.100.11.1.4.1.7
        qosPolicyPeakKbps OBJECT-TYPE
            SYNTAX  INTEGER(1..1000000)
            MAX-ACCESS  read-create
            STATUS  current
            DESCRIPTION
                "Peak information rate."
            ::= { qosPolicyEntry 7 } 
            
--xxx.100.11.1.4.1.8
        qosPolicyConformAction OBJECT-TYPE
            SYNTAX  INTEGER
            	{
            	        transmit(0),
            	    	drop(1),
               		set-dscp-transmit(2), 
               		set-prec-transmit(3)        	
            	}
            MAX-ACCESS  read-create
            STATUS  current
            DESCRIPTION
                "conform-action transmit means send packets without any change when specified speed is not exceeded;
                 conform-action drop means drop packets when specified speed is not exceeded;
                 conform-action set-dscp-transmit specifies to mark down packet DSCP value 
                 according to policed-dscp mapping when specified speed is not exceeded;
                 conform-action set-prec-transmit specifies to mark down packet TOS value 
                 according to policed-dscp mapping when specified speed is not exceeded."
            ::= { qosPolicyEntry 8 } 
            
--xxx.100.11.1.4.1.9
        qosPolicyConformActionChangeValue OBJECT-TYPE
            SYNTAX  INTEGER (0..63)
            MAX-ACCESS  read-create
            STATUS  current
            DESCRIPTION
                "If conform-action is set-dscp-transmit(2),the value is between 0-63;
                 else if conform-action is set-prec-transmit(2),the value is between 0-7."
            ::= { qosPolicyEntry 9 }                                                  

--xxx.100.11.1.4.1.10
        qosPolicyExceedAction OBJECT-TYPE
            SYNTAX  INTEGER
            	{
            	        transmit(0),
            	    	drop(1),
               		policeDscpTransmit(2)         	
            	}
            MAX-ACCESS  read-create
            STATUS  current
            DESCRIPTION
                "exceed-action transmit means send packets without any change when specified speed is exceeded;
                 exceed-action drop means drop packets when specified speed is exceeded;
                 exceed-action policed-dscp-transmit specifies to mark down packet DSCP value 
                 according to policed-dscp mapping when specified speed is exceeded."
            ::= { qosPolicyEntry 10 }
            
--xxx.100.11.1.4.1.11
        qosPolicyViolateAction OBJECT-TYPE
            SYNTAX  INTEGER
            	{
            	        transmit(0),
            	    	drop(1),
               		policeDscpTransmit(2)         	
            	}
            MAX-ACCESS  read-create
            STATUS  current
            DESCRIPTION
                "violate-action transmit means send packets without any change when specified speed is violate;
                 violate-action drop means drop packets when specified speed is violate;
                 violate-action policed-dscp-transmit specifies to mark down packet DSCP value 
                 according to policed-dscp mapping when specified speed is violate."
            ::= { qosPolicyEntry 11 }                  

--xxx.100.11.1.4.1.12
        qosPolicyAggregatePolicer OBJECT-TYPE
            SYNTAX  DisplayString
            MAX-ACCESS  read-create
            STATUS  current
            DESCRIPTION
                "aggregate-policer-name.
                This object be configured only if qosPolicyType 
                in the same row is aggregatePolicer(3)."
            ::= { qosPolicyEntry 12 }   

--xxx.100.11.1.4.1.13
        qosPolicyStatus OBJECT-TYPE
            SYNTAX  INTEGER
            	    {
               		active(1),
               		destroy(2)
            	    }
            MAX-ACCESS  read-create
            STATUS  current
            DESCRIPTION
                " Setting it to  active(1) to creates an entry,setting it to destroy(2) to destroy an entry."
            ::= { qosPolicyEntry 13 } 

--********************************************************************************************************

--xxx.100.11.1.5
qosAggPolicerTable OBJECT-TYPE
    SYNTAX  SEQUENCE OF QosAggPolicerEntry
    MAX-ACCESS  not-accessible
    STATUS  current
            DESCRIPTION
                "qos of AggPolicer list,use it can configure one item AggPolicer,Attention : the get/get next operation can only get snmp cache content,
                please refer to qosshow node for the running configuraton"
            ::= { qos 5 } 

--xxx.100.11.1.5.1
    qosAggPolicerEntry OBJECT-TYPE
        SYNTAX  QosAggPolicerEntry
        MAX-ACCESS  not-accessible
        STATUS  current
        DESCRIPTION
            " index is AggPolicer name."
        INDEX   { qosAggPolicerName }
        ::= { qosAggPolicerTable 1 }
        
    QosAggPolicerEntry
        ::= SEQUENCE
            {
                qosAggPolicerName			DisplayString,
                qosAggPolicerRateKbps			INTEGER,
                qosAggPolicerNormalBurstKbps		INTEGER,
                qosAggPolicerMaximumBurstKbps 		INTEGER,
                qosAggPolicerPeakKbps			INTEGER, 
                qosAggPolicerConformAction		INTEGER,
                qosAggPolicerConformActionChangeValue	INTEGER,
                qosAggPolicerExceedAction 		INTEGER,
                qosAggPolicerViolateAction 		INTEGER,                
                qosAggPolicerStatus			INTEGER                                              
            }

--xxx.100.11.1.5.1.1
        qosAggPolicerName OBJECT-TYPE
            SYNTAX  DisplayString (SIZE(1..32))
            MAX-ACCESS  not-accessible
            STATUS  current
            DESCRIPTION
                "QoS qosAggPolicer name"
            ::= { qosAggPolicerEntry 1 }

--xxx.100.11.1.5.1.2
        qosAggPolicerRateKbps OBJECT-TYPE
            SYNTAX  INTEGER(1..10000000)
            MAX-ACCESS  read-create
            STATUS  current
            DESCRIPTION
                "Rate Bandwidth of After the classification."
            ::= { qosAggPolicerEntry 2 }            

--xxx.100.11.1.5.1.3
        qosAggPolicerNormalBurstKbps OBJECT-TYPE
            SYNTAX  INTEGER(1..1000000)
            MAX-ACCESS  read-create
            STATUS  current
            DESCRIPTION
                "Normal burst kbytes."
            ::= { qosAggPolicerEntry 3 }
            
--xxx.100.11.1.5.1.4
        qosAggPolicerMaximumBurstKbps OBJECT-TYPE
            SYNTAX  INTEGER(1..1000000)
            MAX-ACCESS  read-create
            STATUS  current
            DESCRIPTION
                "Maximum burst kbytes."
            ::= { qosAggPolicerEntry 4 }
            
--xxx.100.11.1.5.1.5
        qosAggPolicerPeakKbps OBJECT-TYPE
            SYNTAX  INTEGER(1..1000000)
            MAX-ACCESS  read-create
            STATUS  current
            DESCRIPTION
                "Peak information rate."
            ::= { qosAggPolicerEntry 5 } 
            
--xxx.100.11.1.5.1.6
        qosAggPolicerConformAction OBJECT-TYPE
            SYNTAX  INTEGER
            	{
            	        transmit(0),
            	    	drop(1),
               		set-dscp-transmit(2), 
               		set-prec-transmit(3)        	
            	}
            MAX-ACCESS  read-create
            STATUS  current
            DESCRIPTION
                "conform-action transmit means send packets without any change when specified speed is not exceeded;
                 conform-action drop means drop packets when specified speed is not exceeded;
                 conform-action set-dscp-transmit specifies to mark down packet DSCP value 
                 according to policed-dscp mapping when specified speed is not exceeded;
                 conform-action set-prec-transmit specifies to mark down packet TOS value 
                 according to policed-dscp mapping when specified speed is not exceeded."
            ::= { qosAggPolicerEntry 6 } 
            
--xxx.100.11.1.5.1.7
        qosAggPolicerConformActionChangeValue OBJECT-TYPE
            SYNTAX  INTEGER (0..63)
            MAX-ACCESS  read-create
            STATUS  current
            DESCRIPTION
                "If conform-action is set-dscp-transmit(2),the value is between 0-63;
                 else if conform-action is set-prec-transmit(2),the value is between 0-7."
            ::= { qosAggPolicerEntry 7 }                                                  

--xxx.100.11.1.5.1.8
        qosAggPolicerExceedAction OBJECT-TYPE
            SYNTAX  INTEGER
            	{
            	        transmit(0),
            	    	drop(1),
               		policeDscpTransmit(2)         	
            	}
            MAX-ACCESS  read-create
            STATUS  current
            DESCRIPTION
                "exceed-action transmit means send packets without any change when specified speed is exceeded;
                 exceed-action drop means drop packets when specified speed is exceeded;
                 exceed-action policed-dscp-transmit specifies to mark down packet DSCP value 
                 according to policed-dscp mapping when specified speed is exceeded."
            ::= { qosAggPolicerEntry 8 }
            
--xxx.100.11.1.5.1.9
        qosAggPolicerViolateAction OBJECT-TYPE
            SYNTAX  INTEGER
            	{
            	        transmit(0),
            	    	drop(1),
               		policeDscpTransmit(2)         	
            	}
            MAX-ACCESS  read-create
            STATUS  current
            DESCRIPTION
                "violate-action transmit means send packets without any change when specified speed is violate;
                 violate-action drop means drop packets when specified speed is violate;
                 violate-action policed-dscp-transmit specifies to mark down packet DSCP value 
                 according to policed-dscp mapping when specified speed is violate."
            ::= { qosAggPolicerEntry 9 }               

--xxx.100.11.1.5.1.10
        qosAggPolicerStatus OBJECT-TYPE
            SYNTAX  INTEGER
            	    {
               		active(1),
               		destroy(2)
            	    }
            MAX-ACCESS  read-create
            STATUS  current
            DESCRIPTION
                " Setting it to  active(1) to creates an entry,setting it to destroy(2) to destroy an entry."
            ::= { qosAggPolicerEntry 10 } 

--********************************************************************************************************

--xxx.100.11.1.6
qosSetTable OBJECT-TYPE
    SYNTAX  SEQUENCE OF QosSetEntry
    MAX-ACCESS  not-accessible
    STATUS  current
            DESCRIPTION
                "remark new dscp or ip precedence for classified flow"
            ::= { qos 6 } 

--xxx.100.11.1.6.1
    qosSetEntry OBJECT-TYPE
        SYNTAX  QosSetEntry
        MAX-ACCESS  not-accessible
        STATUS  current
        DESCRIPTION
            " qosSetTable list of acce index policyname and classmap name."
        INDEX   { qosSetPolicyMapName }
        ::= { qosSetTable 1 }
        
    QosSetEntry
        ::= SEQUENCE
            {
                qosSetPolicyMapName		DisplayString,
                qosSetClassMapName		DisplayString,
		qosSetType		INTEGER,
		qosSetdscp		INTEGER,
		qosSetprecedence	INTEGER,	
		qosSetnextHop		IpAddress,
		qosSetv6Dscp		INTEGER,
		qosSetv6FlowLabel	INTEGER,
		qosSetv6nextHop		DisplayString,
		qosSetCos		       INTEGER,
		qosSetEXPimposition  INTEGER,
    qosSetStatus		       INTEGER                               
            }

--xxx.100.11.1.6.1.1
        qosSetPolicyMapName OBJECT-TYPE
            SYNTAX  DisplayString (SIZE(1..32))
            MAX-ACCESS  not-accessible
            STATUS  current
            DESCRIPTION
                "QoS Policy name"
            ::= { qosSetEntry 1 }

--xxx.100.11.1.6.1.2
        qosSetClassMapName OBJECT-TYPE
            SYNTAX  DisplayString (SIZE(1..32))
            MAX-ACCESS  read-create
            STATUS  current
            DESCRIPTION
                "QoS class map name"
            ::= { qosSetEntry 2 }
            
--xxx.100.11.1.6.1.3
        qosSetType OBJECT-TYPE
            SYNTAX  INTEGER
            	{
            	    	dscp(1),
               		precedence(2),
               		nextHop(3),
               		v6Dscp(4),            		
               		v6FlowLabel(6),
               		v6nextHop(7),
               		cos(8),
               		expimposition(9)           	
            	}
            MAX-ACCESS  read-create
            STATUS  current
            DESCRIPTION
                "qosSetType range:1,2,3,4,5,6,7,8,9
                1   dscp         Set IP DSCP (DiffServ CodePoints);
                2   precedence   Set IP precedence;
                3   nexthop      Set IP nexthop;
                4   dscp         Set IPv6 DSCP (DiffServ CodePoints);
                6   flowlabel    Set IPv6 flowlabel;
		            7   v6nextHop    Set IPv6 nexthop;
                8   cos          Set CoS ;
                9   expimposition Set mpls-experimental-imposition "		
            ::= { qosSetEntry 3 } 
            
--xxx.100.11.1.6.1.4
        qosSetdscp OBJECT-TYPE
            SYNTAX  INTEGER(0..63)
            MAX-ACCESS  read-create
            STATUS  current
            DESCRIPTION
                "remark dscp for the classified flow"
            ::= { qosSetEntry 4 } 

--xxx.100.11.1.6.1.5
        qosSetprecedence OBJECT-TYPE
            SYNTAX  INTEGER(0..7)
            MAX-ACCESS  read-create
            STATUS  current
            DESCRIPTION
                "remark ip precedence for classified flow"
            ::= { qosSetEntry 5 }
             
--xxx.100.11.1.6.1.6
        qosSetnextHop OBJECT-TYPE
            SYNTAX  IpAddress
            MAX-ACCESS  read-create
            STATUS  current
            DESCRIPTION
                "set nexthop for classified flow"
            ::= { qosSetEntry 6 } 
            
--xxx.100.11.1.6.1.7
        qosSetv6Dscp OBJECT-TYPE
            SYNTAX  INTEGER(0..63)
            MAX-ACCESS  read-create
            STATUS  current
            DESCRIPTION
                "remark ipv6 dscp for classified flow"
            ::= { qosSetEntry 7 }
             
--xxx.100.11.1.6.1.8
        qosSetv6FlowLabel OBJECT-TYPE
            SYNTAX  INTEGER(0..1048575)
            MAX-ACCESS  read-create
            STATUS  current
            DESCRIPTION
                "remark ipv6 flow lable for classified flow"
            ::= { qosSetEntry 8 } 
            
--xxx.100.11.1.6.1.9
        qosSetv6nextHop OBJECT-TYPE
            SYNTAX  DisplayString
            MAX-ACCESS  read-create
            STATUS  current
            DESCRIPTION
                "set IPv6 nexthop for classified flow"
            ::= { qosSetEntry 9 }

--xxx.100.11.1.6.1.10
        qosSetCos OBJECT-TYPE
            SYNTAX  INTEGER(0..7)
            MAX-ACCESS  read-create
            STATUS  current
            DESCRIPTION
                "remark cos for classified flow"
            ::= { qosSetEntry 10 } 
            
--xxx.100.11.1.6.1.11
        qosSetEXPimposition OBJECT-TYPE
            SYNTAX  INTEGER(0..7)
            MAX-ACCESS  read-create
            STATUS  current
            DESCRIPTION
                "remark MPLS EXP value for classified flow"
            ::= { qosSetEntry 11 }             

--xxx.100.11.1.6.1.12
        qosSetStatus OBJECT-TYPE
            SYNTAX  INTEGER
            	    {
               		active(1),
               		destroy(2)
            	    }
            MAX-ACCESS  read-create
            STATUS  current
            DESCRIPTION
                " Setting it to  active(1) to creates an entry,setting it to destroy(2) to destroy an entry."
            ::= { qosSetEntry 12 } 

--********************************************************************************************************

--xxx.100.11.1.7
qosPortBindTable OBJECT-TYPE
    SYNTAX  SEQUENCE OF QosPortBindEntry
    MAX-ACCESS  not-accessible
    STATUS  current
            DESCRIPTION
                "Apply a policy map to the specified port."
            ::= { qos 7 } 

--xxx.100.11.1.7.1
    qosPortBindEntry OBJECT-TYPE
        SYNTAX  QosPortBindEntry
        MAX-ACCESS  not-accessible
        STATUS  current
        DESCRIPTION
            "the index of this  entry is port-index and policy-map"
        INDEX   { qosPortBindIndex , qosPortBindPolicy }
        ::= { qosPortBindTable 1 }

    QosPortBindEntry
        ::= SEQUENCE
            {
                qosPortBindIndex		INTEGER,
                qosPortBindPolicy		DisplayString,
		qosPortBindType			INTEGER
	    }  
	    
--xxx.100.11.1.7.1.1
        qosPortBindIndex OBJECT-TYPE
            SYNTAX  INTEGER
            MAX-ACCESS  not-accessible
            STATUS  current
            DESCRIPTION
                "QoS Port Index"
            ::= { qosPortBindEntry 1 }

--xxx.100.11.1.7.1.2
        qosPortBindPolicy OBJECT-TYPE
            SYNTAX  DisplayString (SIZE(1..16))
            MAX-ACCESS  not-accessible
            STATUS  current
            DESCRIPTION
                "QoS Policy name"
            ::= { qosPortBindEntry 2 }
            
--xxx.100.11.1.7.1.3
        qosPortBindType OBJECT-TYPE
            SYNTAX  INTEGER
            	{
            	    input(1),
               		output(2),  
               		noinput(3),
               		nooutput(4)            	
            	}
            MAX-ACCESS  read-create
            STATUS  current
            DESCRIPTION
                " input(1),bind the policy-map to ingress port;
               		output(2),bind the policy-map to egress port;
               		noinput(3),unbind the policy-map to ingress port;
               		nooutput(4), unbind the policy-map to egress port"
            ::= { qosPortBindEntry 3 } 

--********************************************************************************************************

--xxx.100.11.1.8
qosPortQueueTable OBJECT-TYPE
    SYNTAX  SEQUENCE OF QosPortQueueEntry
    MAX-ACCESS  not-accessible
    STATUS  current
            DESCRIPTION
                "set golbal qos WRR weight"
            ::= { qos 8 } 

--xxx.100.11.1.8.1
    qosPortQueueEntry OBJECT-TYPE
        SYNTAX  QosPortQueueEntry
        MAX-ACCESS  not-accessible
        STATUS  current
        DESCRIPTION
            " set port qos WRR weight,index is port index."
        INDEX   { qosPortQueueIndex }
        ::= { qosPortQueueTable 1 }

    QosPortQueueEntry
        ::= SEQUENCE
            {
                qosPortQueueIndex		INTEGER,
                qosPortQueueWeight1		INTEGER,
                qosPortQueueWeight2		INTEGER,
                qosPortQueueWeight3		INTEGER,
                qosPortQueueWeight4		INTEGER,
                qosPortQueueWeight5		INTEGER,
                qosPortQueueWeight6		INTEGER,
                qosPortQueueWeight7		INTEGER,
                qosPortQueueWeight8		INTEGER,
		qosPortQueueStatus		INTEGER
	    }  
	    
--xxx.100.11.1.8.1.1
        qosPortQueueIndex OBJECT-TYPE
            SYNTAX  INTEGER
            MAX-ACCESS  not-accessible
            STATUS  current
            DESCRIPTION
                "QoS Port Index"
            ::= { qosPortQueueEntry 1 }

--xxx.100.11.1.8.1.2
        qosPortQueueWeight1 OBJECT-TYPE
            SYNTAX  INTEGER
            MAX-ACCESS  read-create
            STATUS  current
            DESCRIPTION
                "WRR weight,range is 0~15."
            ::= { qosPortQueueEntry 2 }

--xxx.100.11.1.8.1.3
        qosPortQueueWeight2 OBJECT-TYPE
            SYNTAX  INTEGER
            MAX-ACCESS  read-create
            STATUS  current
            DESCRIPTION
                "WRR weight,range is 0~15."
            ::= { qosPortQueueEntry 3 }

--xxx.100.11.1.8.1.4
        qosPortQueueWeight3 OBJECT-TYPE
            SYNTAX  INTEGER
            MAX-ACCESS  read-create
            STATUS  current
            DESCRIPTION
                "WRR weight,range is 0~15."
            ::= { qosPortQueueEntry 4 }
 
 --xxx.100.11.1.8.1.5
        qosPortQueueWeight4 OBJECT-TYPE
            SYNTAX  INTEGER
            MAX-ACCESS  read-create
            STATUS  current
            DESCRIPTION
                "WRR weight,range is 0~15."
            ::= { qosPortQueueEntry 5 }
 
 --xxx.100.11.1.8.1.6
        qosPortQueueWeight5 OBJECT-TYPE
            SYNTAX  INTEGER
            MAX-ACCESS  read-create
            STATUS  current
            DESCRIPTION
                "WRR weight,range is 0~15."
            ::= { qosPortQueueEntry 6 }
 
 --xxx.100.11.1.8.1.7
        qosPortQueueWeight6 OBJECT-TYPE
            SYNTAX  INTEGER
            MAX-ACCESS  read-create
            STATUS  current
            DESCRIPTION
                "WRR weight,range is 0~15."
            ::= { qosPortQueueEntry 7 }
 
 --xxx.100.11.1.8.1.8
        qosPortQueueWeight7 OBJECT-TYPE
            SYNTAX  INTEGER
            MAX-ACCESS  read-create
            STATUS  current
            DESCRIPTION
                "WRR weight,range is 0~15."
            ::= { qosPortQueueEntry 8 }

 --xxx.100.11.1.8.1.9
        qosPortQueueWeight8 OBJECT-TYPE
            SYNTAX  INTEGER
            MAX-ACCESS  read-create
            STATUS  current
            DESCRIPTION
                "WRR weight,range is 0~15."
            ::= { qosPortQueueEntry 9 }

 --xxx.100.11.1.8.1.10
        qosPortQueueStatus OBJECT-TYPE
            SYNTAX  INTEGER
            	    {
               		active(1),
               		destroy(2)
            	    }
            MAX-ACCESS  read-create
            STATUS  current
            DESCRIPTION
                "Setting it to active(1) creates an entry.Setting it to destroy(2) destroys an entry."
            ::= { qosPortQueueEntry 10 } 

--********************************************************************************************************
                    	                                     
--********************************************************************************************************
--xxx.100.11.1.10
    qosMap         	    OBJECT IDENTIFIER ::= { qos 10 } 

--set class of service(CoS)-to-Differentiated Services Code Point (DSCP) map,DSCP-to-CoS map,DSCP-to-DSCP-mutation map,IP-precedence-to-DSCP map and policed-DSCP map
--xxx.100.11.1.10.1
        qosMapType OBJECT-TYPE
            SYNTAX  INTEGER
            	{
            	    	cosDscp(1),
               		dscpCos(2),
               		dscpMutation(3),
               		ipPrecDscp(4),
               		policedDscp(5),
               		expdscp(6),
               		dscpexp(7)      	
            	}
            MAX-ACCESS  read-create
            STATUS  current
            DESCRIPTION
                "qosMapType range is 1~5.1 mls qos map cos-dscp <dscp1...dscp8>;
                 2 mls qos map  dscp-cos <dscp-list> to <cos>;
                 3 mls qos map  dscp-mutation <dscp-mutation-name> <in-dscp> to <out-dscp>;
		 4  mls qos map ip-prec-dscp <dscp1...dscp8>; 
		 5  mls qos map policed-dscp <dscp-list> to <mark-down-dscp>;
		 6  mls qos map exp-dscp <dscp-value-list>;
		 7  mls qos map dscp-exp <dscp-value-list> to <exp>
		 When you want to configure the Map of DSCP to COS,please configure the qosMapType==2 firstly,
		  input the dscp(1~8) optionally, then  configure the qosMapCos , valid/invalid the qosMapStatus finally."
								
            ::= { qosMap  1 }

--xxx.100.11.1.10.2
        qosMapDscp1 OBJECT-TYPE
            SYNTAX  INTEGER
            MAX-ACCESS  read-create
            STATUS  current
            DESCRIPTION
                "DSCP-CoS map,DSCP range is 0~63"
            ::= { qosMap  2 }

--xxx.100.11.1.10.3
        qosMapDscp2 OBJECT-TYPE
            SYNTAX  INTEGER
            MAX-ACCESS  read-create
            STATUS  current
            DESCRIPTION
                "DSCP-CoS map,DSCP range is 0~63"
            ::= { qosMap  3 }

--xxx.100.11.1.10.4
        qosMapDscp3 OBJECT-TYPE
            SYNTAX  INTEGER
            MAX-ACCESS  read-create
            STATUS  current
            DESCRIPTION
                "DSCP-CoS map,DSCP range is 0~63"
            ::= { qosMap  4 }            
            
--xxx.100.11.1.10.5
        qosMapDscp4 OBJECT-TYPE
            SYNTAX  INTEGER
            MAX-ACCESS  read-create
            STATUS  current
            DESCRIPTION
                "DSCP-CoS map,DSCP range is 0~63"
            ::= { qosMap  5 }
            
--xxx.100.11.1.10.6
        qosMapDscp5 OBJECT-TYPE
            SYNTAX  INTEGER
            MAX-ACCESS  read-create
            STATUS  current
            DESCRIPTION
                "DSCP-CoS map,DSCP range is 0~63"
            ::= { qosMap  6 }
            
--xxx.100.11.1.10.7
        qosMapDscp6 OBJECT-TYPE
            SYNTAX  INTEGER
            MAX-ACCESS  read-create
            STATUS  current
            DESCRIPTION
                "DSCP-CoS map,DSCP range is 0~63"
            ::= { qosMap  7 }

--xxx.100.11.1.10.8
        qosMapDscp7 OBJECT-TYPE
            SYNTAX  INTEGER
            MAX-ACCESS  read-create
            STATUS  current
            DESCRIPTION
                "DSCP-CoS map,DSCP range is 0~63"
            ::= { qosMap  8 }

--xxx.100.11.1.10.9
        qosMapDscp8 OBJECT-TYPE
            SYNTAX  INTEGER
            MAX-ACCESS  read-create
            STATUS  current
            DESCRIPTION
                "DSCP-CoS map,DSCP range is 0~63"
            ::= { qosMap  9 }

--xxx.100.11.1.10.10
        qosMapCos OBJECT-TYPE
            SYNTAX  INTEGER
            MAX-ACCESS  read-create
            STATUS  current
            DESCRIPTION
                "the cos which DSCP map to "
            ::= { qosMap  10 }
            
--xxx.100.11.1.10.11
        qosMapEXP OBJECT-TYPE
            SYNTAX  INTEGER(0..7)
            MAX-ACCESS  read-create
            STATUS  current
            DESCRIPTION
                "the EXP value which DSCP map to "
            ::= { qosMap  11 }         
--xxx.100.11.1.10.12
        qosMapMarkDownDscp OBJECT-TYPE
            SYNTAX  INTEGER
            MAX-ACCESS  read-create
            STATUS  current
            DESCRIPTION
                "the dscp after mark down"
            ::= { qosMap  12 }
            
--xxx.100.11.1.10.13
        qosMapMarkDownType OBJECT-TYPE
            SYNTAX  INTEGER
                    {
               		normal-burst(0),
               		max-burst(1)
            	    }
            MAX-ACCESS  read-create
            STATUS  current
            DESCRIPTION
                "normal-burst:markdown map used by the exceed-action;max-burst:markdown map used by the violate-action."
            ::= { qosMap  13 }                         

--xxx.100.11.1.10.14
        qosMapMutationName OBJECT-TYPE
            SYNTAX  DisplayString (SIZE(1..16))
            MAX-ACCESS  read-create
            STATUS  current
            DESCRIPTION
                "map name"
            ::= { qosMap  14 }   
            
--xxx.100.11.1.10.15
        qosMapMutationOut OBJECT-TYPE
            SYNTAX  INTEGER
            MAX-ACCESS  read-create
            STATUS  current
            DESCRIPTION
                "egress DSCP,only one,eight ingress DSCP value map to one egress value"
            ::= { qosMap  15 }                       
--xxx.100.11.1.10.16
        qosMapStatus OBJECT-TYPE
            SYNTAX  INTEGER
            	    {
               		active(1),
               		destroy(2)
            	    }
            MAX-ACCESS  read-create
            STATUS  current
            DESCRIPTION
                " Setting it to  active(1) to creates an entry,setting it to destroy(2) to destroy an entry."
            ::= { qosMap 16 } 


--xxx.100.11
    showqos        	   	  OBJECT IDENTIFIER ::= { qos 11 }    
    
--xxx.100.16.2.1
showclassmapTable OBJECT-TYPE 
    SYNTAX  SEQUENCE OF ShowclassmapEntry
    MAX-ACCESS  not-accessible
    STATUS  current
    DESCRIPTION
        " show class map table"
    ::= { showqos   1}
            
--xxx.100.16.2.1.1
showclassmapEntry OBJECT-TYPE
        SYNTAX  ShowclassmapEntry
        MAX-ACCESS  not-accessible
        STATUS  current
        DESCRIPTION
            " show class map entry"
        INDEX   { showclassmapname}
        ::= { showclassmapTable 1 }

ShowclassmapEntry
        ::= SEQUENCE
            {
                showclassmapname               			DisplayString,
                showclassmapmatch				DisplayString
            }
            
--xxx.100.16.2.1.1.1
showclassmapname  OBJECT-TYPE
            SYNTAX  DisplayString (SIZE(1..128))
            MAX-ACCESS  not-accessible
            STATUS  current
            DESCRIPTION
                " classmap name"
            ::= { showclassmapEntry 1 }
            
--xxx.100.16.2.1.1.2         
showclassmapmatch  OBJECT-TYPE
	SYNTAX      DisplayString (SIZE(1..512))	
        MAX-ACCESS  read-only
        STATUS      current
        DESCRIPTION "one item classmap match rule"
        ::= { showclassmapEntry 2 }  


--xxx.100.16.2.1
showpolicymapTable OBJECT-TYPE 
    SYNTAX  SEQUENCE OF ShowpolicymapEntry
    MAX-ACCESS  not-accessible
    STATUS  current
    DESCRIPTION
        " show policy list"
    ::= { showqos   2}
            
--xxx.100.16.2.1.1
showpolicymapEntry OBJECT-TYPE
        SYNTAX  ShowpolicymapEntry
        MAX-ACCESS  not-accessible
        STATUS  current
        DESCRIPTION
            " policy map entry"
        INDEX   { showpolicymapname}
        ::= { showpolicymapTable 1 }

ShowpolicymapEntry
        ::= SEQUENCE
            {
                showpolicymapname               		DisplayString,
                showpolicymapcontent				DisplayString
            }
            
--xxx.100.16.2.1.1.1
showpolicymapname  OBJECT-TYPE
            SYNTAX  DisplayString (SIZE(1..128))
            MAX-ACCESS  not-accessible
            STATUS  current
            DESCRIPTION
                " policy name"
            ::= { showpolicymapEntry 1 }
            
--xxx.100.16.2.1.1.2         
showpolicymapcontent  OBJECT-TYPE
	SYNTAX      DisplayString (SIZE(1..512))	
        MAX-ACCESS  read-only
        STATUS      current
        DESCRIPTION "the match classmap and all defined other rules"
        ::= { showpolicymapEntry 2 }        
        
        
--xxx.100.16.2.1
showqosaggregatepolicerTable OBJECT-TYPE 
    SYNTAX  SEQUENCE OF ShowqosaggregatepolicerEntry
    MAX-ACCESS  not-accessible
    STATUS  current
    DESCRIPTION
        " display aggregatepolicer list"
    ::= { showqos   3}
            
--xxx.100.16.2.1.1
showqosaggregatepolicerEntry OBJECT-TYPE
        SYNTAX  ShowqosaggregatepolicerEntry
        MAX-ACCESS  not-accessible
        STATUS  current
        DESCRIPTION
            " aggregatepolicer entry,index is showqosaggregatepolicername"
        INDEX   { showqosaggregatepolicername}
        ::= { showqosaggregatepolicerTable 1 }

ShowqosaggregatepolicerEntry
        ::= SEQUENCE
            {
                showqosaggregatepolicername               		DisplayString,
                showqosaggregatepolicercontent				DisplayString
            }
            
--xxx.100.16.2.1.1.1
showqosaggregatepolicername  OBJECT-TYPE
            SYNTAX  DisplayString (SIZE(1..128))
            MAX-ACCESS  not-accessible
            STATUS  current
            DESCRIPTION
                " aggregatepolicer name"
            ::= { showqosaggregatepolicerEntry 1 }
            
--xxx.100.16.2.1.1.2         
showqosaggregatepolicercontent  OBJECT-TYPE
	SYNTAX      DisplayString (SIZE(1..512))	
        MAX-ACCESS  read-only
        STATUS      current
        DESCRIPTION "aggregatepolicer parameter"
        ::= { showqosaggregatepolicerEntry 2 }        


--xxx.100.16.2.1
showmlsqosinterfaceTable OBJECT-TYPE 
    SYNTAX  SEQUENCE OF ShowmlsqosinterfaceEntry
    MAX-ACCESS  not-accessible
    STATUS  current
    DESCRIPTION
        " show port qos configuration"
    ::= { showqos   4}
            
--xxx.100.16.2.1.1
showmlsqosinterfaceEntry OBJECT-TYPE
        SYNTAX  ShowmlsqosinterfaceEntry
        MAX-ACCESS  not-accessible
        STATUS  current
        DESCRIPTION
            " showmlsqosinterfaceTable,index is port-index"
        INDEX   { showmlsqosinterfaceIndex}
        ::= { showmlsqosinterfaceTable 1 }

ShowmlsqosinterfaceEntry
        ::= SEQUENCE
            {
                showmlsqosinterfaceIndex               			INTEGER,
                showmlsqosinterfaceqoscontent				DisplayString
            }
            
--xxx.100.16.2.1.1.1
showmlsqosinterfaceIndex  OBJECT-TYPE
            SYNTAX  INTEGER 
            MAX-ACCESS  not-accessible
            STATUS  current
            DESCRIPTION
                " port index"
            ::= { showmlsqosinterfaceEntry 1 }
            
--xxx.100.16.2.1.1.2         
showmlsqosinterfaceqoscontent  OBJECT-TYPE
	SYNTAX      DisplayString (SIZE(1..512))	
        MAX-ACCESS  read-only
        STATUS      current
        DESCRIPTION "qos port configuration"
        ::= { showmlsqosinterfaceEntry 2 }    
        
--xxx.100.9
    showmlsqosmaps        	   	  OBJECT IDENTIFIER ::= { showqos 5 }   

--xxx.100.16.1.1
        showmlsqosmapscosdscp OBJECT-TYPE
            SYNTAX      DisplayString (SIZE(1..512))     	
            MAX-ACCESS  read-only
            STATUS  current
            DESCRIPTION
                "cos-dscp map "
            ::= { showmlsqosmaps 1 }

--xxx.100.16.1.2
        showmlsqosmapscosqueue OBJECT-TYPE
            SYNTAX      DisplayString (SIZE(1..512))                  
            MAX-ACCESS  read-only
            STATUS  current
            DESCRIPTION
                "COS-wrr-queue map"
            ::= { showmlsqosmaps 2 }     
--xxx.100.16.1.3
        showmlsqosmapsdscpcos OBJECT-TYPE
            SYNTAX      DisplayString (SIZE(1..512))                     	
            MAX-ACCESS  read-only
            STATUS  current
            DESCRIPTION
                "DSCP-COS map"
            ::= { showmlsqosmaps  3 }

--xxx.100.16.1.4
        showmlsqosmapsipprecdscp OBJECT-TYPE
            SYNTAX      DisplayString (SIZE(1..512))              
            MAX-ACCESS  read-only
            STATUS  current
            DESCRIPTION
                "IP precedence to DSCP map"
            ::= { showmlsqosmaps  4 }  
--xxx.100.16.1.5
        showmlsqosmapspoliceddscp OBJECT-TYPE
            SYNTAX      DisplayString (SIZE(1..512))                   	
            MAX-ACCESS  read-only
            STATUS  current
            DESCRIPTION
                " DSCP mark down map"
            ::= { showmlsqosmaps  5 }   
            
--xxx.100.16.1.6
        showmlsqosmapspoliceddscpnormalburst OBJECT-TYPE
            SYNTAX      DisplayString (SIZE(1..512))                   	
            MAX-ACCESS  read-only
            STATUS  current
            DESCRIPTION
                " Normal Burst Policed-dscp map"
            ::= { showmlsqosmaps  6 }                
              
--xxx.100.16.1.7
        showmlsqosmapsexpdscp OBJECT-TYPE
            SYNTAX      DisplayString (SIZE(1..512))                    	
            MAX-ACCESS  read-only
            STATUS  current
            DESCRIPTION
                " EXP to DSCP map"
            ::= { showmlsqosmaps  7 } 
            
--xxx.100.16.1.8
        showmlsqosmapsdscpexp OBJECT-TYPE
            SYNTAX      DisplayString (SIZE(1..512))                    	
            MAX-ACCESS  read-only
            STATUS  current
            DESCRIPTION
                " DSCP to EXP map"
            ::= { showmlsqosmaps  8 } 
            
--xxx.100.16.2.1
showmlsqosmapsdscpmutationTable OBJECT-TYPE 
    SYNTAX  SEQUENCE OF ShowmlsqosmapsdscpmutationEntry
    MAX-ACCESS  not-accessible
    STATUS  current
    DESCRIPTION
        " ingress DSCP to egress DSCP map"
    ::= { showqos   6}
            
--xxx.100.16.2.1.1
showmlsqosmapsdscpmutationEntry OBJECT-TYPE
        SYNTAX  ShowmlsqosmapsdscpmutationEntry
        MAX-ACCESS  not-accessible
        STATUS  current
        DESCRIPTION
            "index is dscpmutationname"
        INDEX   { showmlsqosmapsdscpmutationname}
        ::= { showmlsqosmapsdscpmutationTable 1 }

ShowmlsqosmapsdscpmutationEntry
        ::= SEQUENCE
            {
                showmlsqosmapsdscpmutationname               			DisplayString,
                showmlsqosmapsdscpmutationcontent				DisplayString
            }
            
--xxx.100.16.2.1.1.1
showmlsqosmapsdscpmutationname  OBJECT-TYPE
            SYNTAX  DisplayString  (SIZE(1..128))
            MAX-ACCESS  not-accessible
            STATUS  current
            DESCRIPTION
                " dscpmutationname."
            ::= { showmlsqosmapsdscpmutationEntry 1 }
            
--xxx.100.16.2.1.1.2         
showmlsqosmapsdscpmutationcontent  OBJECT-TYPE
	SYNTAX      DisplayString (SIZE(1..512))	
        MAX-ACCESS  read-only
        STATUS      current
        DESCRIPTION "DSCP-DSCP map"
        ::= { showmlsqosmapsdscpmutationEntry 2 }                                 
--********************************************************************************************************
--********************************************************************************************************

--xxx.100.12.1
mirrorDestTable OBJECT-TYPE 
    SYNTAX  SEQUENCE OF MirrorDestEntry
    MAX-ACCESS  not-accessible
    STATUS  current
    DESCRIPTION
        "Destination port for mirrored packets."
    ::= { primirror   1}
            
--xxx.100.12.1.1
mirrorDestEntry OBJECT-TYPE
        SYNTAX  MirrorDestEntry
        MAX-ACCESS  not-accessible
        STATUS  current
        DESCRIPTION
            "Destination port for mirrored packets."
        INDEX   { mirrorDestSession }
        ::= { mirrorDestTable 1 }

MirrorDestEntry
        ::= SEQUENCE
            {
                mirrorDestSession          INTEGER,
                mirrorDestPort		   DisplayString,
                mirrorDestStatus	   INTEGER
            }
            
--xxx.100.12.1.1.1       
mirrorDestSession   OBJECT-TYPE
	SYNTAX      INTEGER (1..4)	
        MAX-ACCESS  read-only
        STATUS      current
        DESCRIPTION "Session ID."
        ::= { mirrorDestEntry 1 } 
          
--xxx.100.12.1.1.2       
mirrorDestPort   OBJECT-TYPE
	SYNTAX      DisplayString(SIZE(1..20))		
        MAX-ACCESS  read-create
        STATUS      current
        DESCRIPTION "mirror destination port  eg:Ethernet1/1."
        ::= { mirrorDestEntry 2 }   

--xxx.100.12.1.1.3       
mirrorDestStatus   OBJECT-TYPE
	SYNTAX      INTEGER
		    {
            	    
               		active(1),
               		destroy(2)		    	
		    }		
        MAX-ACCESS  read-create
        STATUS      current
        DESCRIPTION "Status."
        ::= { mirrorDestEntry 3 } 
        
--********************************************************************************************************

--xxx.100.12.2
mirrorSrcPortTable OBJECT-TYPE 
    SYNTAX  SEQUENCE OF MirrorSrcPortEntry
    MAX-ACCESS  not-accessible
    STATUS  current
    DESCRIPTION
        "Src port for mirrored packets."
    ::= { primirror   2}
            
--xxx.100.12.2.1
mirrorSrcPortEntry OBJECT-TYPE
        SYNTAX  MirrorSrcPortEntry
        MAX-ACCESS  not-accessible
        STATUS  current
        DESCRIPTION
            "Src port for mirrored packets."
        INDEX   { mirrorSrcPortSession , mirrorSrcPortDirect }
        ::= { mirrorSrcPortTable 1 }

MirrorSrcPortEntry
        ::= SEQUENCE
            {
                mirrorSrcPortSession           INTEGER,
                mirrorSrcPortDirect	       INTEGER,
                mirrorSrcPort		       DisplayString,
                mirrorSrcPortStatus            INTEGER
            }
            
--xxx.100.12.2.1.1       
mirrorSrcPortSession   OBJECT-TYPE
	SYNTAX      INTEGER (1..4)	
        MAX-ACCESS  read-only
        STATUS      current
        DESCRIPTION "Session ID."
        ::= { mirrorSrcPortEntry 1 } 
          
--xxx.100.12.2.1.2       
mirrorSrcPortDirect   OBJECT-TYPE
	SYNTAX      INTEGER
		{
               		rx(1),
               		tx(2)		
		}	
        MAX-ACCESS  read-only
        STATUS      current
        DESCRIPTION "Direction of  mirror."
        ::= { mirrorSrcPortEntry 2 }   
        
--xxx.100.12.2.1.3       
mirrorSrcPort   OBJECT-TYPE
	SYNTAX      DisplayString(SIZE(1..512))	
        MAX-ACCESS  read-create
        STATUS      current
        DESCRIPTION "mirror source port. eg:Ethernet1/1."
        ::= { mirrorSrcPortEntry 3 } 
        
--xxx.100.12.2.1.4       
mirrorSrcPortStatus   OBJECT-TYPE
	SYNTAX      INTEGER
		    {
            	    	
               		active(1),
               		destroy(2)		    	
		    }		
        MAX-ACCESS  read-create
        STATUS      current
        DESCRIPTION "Status."
        ::= { mirrorSrcPortEntry 4 }         
        
--********************************************************************************************************
--********************************************************************************************************
--xxx.100.11.2
    qos3         	    OBJECT IDENTIFIER ::= { priQos 2 } 
    
--********************************************************************************************************    

--xxx.100.11.2.1
qos3PolicyMapGroupTable OBJECT-TYPE
    SYNTAX  SEQUENCE OF Qos3PolicyMapGroupEntry
    MAX-ACCESS  not-accessible
    STATUS  current
            DESCRIPTION
                "this table is used for building a policy and mapping the named policy to number,
             if you want to configure a policy,you must map at here."
            ::= { qos3 1 } 

--xxx.100.11.2.1.1
    qos3PolicyMapGroupEntry OBJECT-TYPE
        SYNTAX  Qos3PolicyMapGroupEntry
        MAX-ACCESS  not-accessible
        STATUS  current
        DESCRIPTION
            "entry for policy map group."
        INDEX   { qos3PolicyMapGroupIndex }
        ::= { qos3PolicyMapGroupTable 1 } 

    Qos3PolicyMapGroupEntry
        ::= SEQUENCE
            {
                qos3PolicyMapGroupIndex			INTEGER,
                qos3PolicyMapGroupName			DisplayString,
                qos3PolicyMapGroupIsExt       INTEGER,                
                qos3PolicyMapGroupStatus			INTEGER
        
            }

--xxx.100.11.2.1.1.1
qos3PolicyMapGroupIndex OBJECT-TYPE
    SYNTAX  INTEGER
            MAX-ACCESS  read-only
            STATUS  current
            DESCRIPTION
                "the range is 0-(2^64 - 1)."
            ::= { qos3PolicyMapGroupEntry 1 } 
                               
--xxx.100.11.2.1.1.2
qos3PolicyMapGroupName OBJECT-TYPE
    SYNTAX  DisplayString(SIZE(1..64))
            MAX-ACCESS  read-write
            STATUS  current
            DESCRIPTION
                "the policy name"
            ::= { qos3PolicyMapGroupEntry 2 } 
            
--xxx.100.11.2.1.1.3
qos3PolicyMapGroupIsExt OBJECT-TYPE
    SYNTAX  INTEGER
            {
               disable(0),
               enable(1)
            }
            MAX-ACCESS  read-write
            STATUS  current
            DESCRIPTION
                "indicate that whether the policy used on extand field processor."
            ::= { qos3PolicyMapGroupEntry 3 } 

--xxx.100.11.2.1.1.4
qos3PolicyMapGroupStatus OBJECT-TYPE
    SYNTAX  INTEGER
            {
              createAndGo(0),
              active(1),
              destroy(2)
            }
            MAX-ACCESS  read-write
            STATUS  current
            DESCRIPTION
                "the status of qos3PolicyMapGroupTable"
            ::= { qos3PolicyMapGroupEntry 4 } 
            
--*********************************************************************************************************

--xxx.100.11.2.2
qos3ClassMapTable OBJECT-TYPE
    SYNTAX  SEQUENCE OF Qos3ClassMapEntry
    MAX-ACCESS  not-accessible
    STATUS  current
            DESCRIPTION
                "this table is used for configuring the filter rule of qos"
            ::= { qos3 2 } 

--xxx.100.11.2.2.1
    qos3ClassMapEntry OBJECT-TYPE
        SYNTAX  Qos3ClassMapEntry
        MAX-ACCESS  not-accessible
        STATUS  current
        DESCRIPTION
            "entry for class map."
        INDEX   { qos3ClassMapName }
        ::= { qos3ClassMapTable 1 } 

    Qos3ClassMapEntry
        ::= SEQUENCE
            {
                qos3ClassMapName			     DisplayString,
                qos3ClassMapType			     INTEGER,
                qos3ClassMapValue           DisplayString, 
                qos3ClassMapUsedTime        INTEGER,
                qos3ClassMapStatus         INTEGER
    
            }

--xxx.100.11.2.2.1.1
qos3ClassMapName OBJECT-TYPE
    SYNTAX  DisplayString(SIZE(1..64))
            MAX-ACCESS  read-only
            STATUS  current
            DESCRIPTION
                "the name of class"
            ::= { qos3ClassMapEntry 1 }
            
--xxx.100.11.2.2.1.2
qos3ClassMapType OBJECT-TYPE
    SYNTAX  INTEGER
             {
              cos(0),
              dscp(1),
              ipPrecedence(2),
              ipv6Dscp(3),
              ipv6Flowlabel(4),
              exp(5),
              vlan(6),
              aclIndex(7)
             
             }
            MAX-ACCESS  read-write
            STATUS  current
            DESCRIPTION
                "the clss type that you want to matching."
            ::= { qos3ClassMapEntry 2 }                      

--xxx.100.11.2.2.1.3
qos3ClassMapValue OBJECT-TYPE
    SYNTAX  DisplayString
            MAX-ACCESS  read-write
            STATUS  current
            DESCRIPTION
                "the value of you choosed type at last node,the limits: cos <0-7> dscp <0-63> ipPrecedence<0-7> ipv6Dscp<0-63> vlan <1-4094> ipv6Flowlabel<0-1048575>
                  exp is not support now.except aclindex,you can  config 8 parameters at most,for example,if you choose the
                  type of cos,you can config 0,1,2,3,4,5,6,7 or 0,1 at here."
            ::= { qos3ClassMapEntry 3 } 
                        
--xxx.100.11.2.2.1.3
qos3ClassMapUsedTime OBJECT-TYPE
    SYNTAX  INTEGER
            MAX-ACCESS  read-only
            STATUS  current
            DESCRIPTION
                "display how many times the class used."
            ::= { qos3ClassMapEntry 4 } 
                                    
--xxx.100.11.2.2.1.5
qos3ClassMapStatus OBJECT-TYPE
    SYNTAX  INTEGER
            {
              createAndGo(0),
              active(1),
              destroy(2),
              remove(3)
            
            }
            MAX-ACCESS  read-write
            STATUS  current
            DESCRIPTION
                "the status of qos3ClassMapTable,destroy(2) will destroy the whole class-map,remove(3) just clear the value of qos3ClassMapValue."
            ::= { qos3ClassMapEntry 5 }   

--********************************************************************************************************
--xxx.100.11.2.3
qos3AggregatePolicyTable OBJECT-TYPE
    SYNTAX  SEQUENCE OF Qos3AggregatePolicyEntry
    MAX-ACCESS  not-accessible
    STATUS  current
            DESCRIPTION
                "this table is used for configuring aggregate policy."
            ::= { qos3 3 } 

--xxx.100.11.2.3.1
    qos3AggregatePolicyEntry OBJECT-TYPE
        SYNTAX  Qos3AggregatePolicyEntry
        MAX-ACCESS  not-accessible
        STATUS  current
        DESCRIPTION
            "entry for aggregate policy."
        INDEX   { qos3AggPolicyMapName }
        ::= { qos3AggregatePolicyTable 1 } 

    Qos3AggregatePolicyEntry
        ::= SEQUENCE
            {
                qos3AggPolicyMapName			         DisplayString,
                qos3AggPolicyCIRKbps			         INTEGER,
                qos3AggPolicyCBSKbps               INTEGER,                
                qos3AggPolicyPBSKbps			         INTEGER,
                qos3AggPolicyPIRKbps               INTEGER,
                qos3AggPolicyConformAction	       BITS,
                qos3AggPolicyconformSetCos         INTEGER,
                qos3AggPolicyconformSetDscp        INTEGER,
                qos3AggPolicyconformSetPrec        INTEGER,
                qos3AggPolicyconformSetIntp        INTEGER,
                qos3AggPolicyconformSetDp          INTEGER,
                qos3AggPolicyExceedAction          BITS,
                qos3AggPolicyExceedSetCos          INTEGER,
                qos3AggPolicyExceedSetDscp         INTEGER,
                qos3AggPolicyExceedSetPrec         INTEGER,
                qos3AggPolicyExceedSetIntp         INTEGER,
                qos3AggPolicyExceedSetDp           INTEGER,
                qos3AggPolicyViolateAction         BITS,
                qos3AggPolicyViolateSetCos         INTEGER,
                qos3AggPolicyViolateSetDscp        INTEGER,
                qos3AggPolicyViolateSetPrec        INTEGER,
                qos3AggPolicyViolateSetIntp        INTEGER,
                qos3AggPolicyViolateSetDp          INTEGER,
                qos3AggPolicyStatus                INTEGER
    
            }

--xxx.100.11.2.3.1.1
qos3AggPolicyMapName OBJECT-TYPE
    SYNTAX  DisplayString(SIZE(1..64))
            MAX-ACCESS  read-only
            STATUS  current
            DESCRIPTION
                "the name of aggregate policy."
            ::= { qos3AggregatePolicyEntry 1 }

--xxx.100.11.2.3.1.2
qos3AggPolicyCIRKbps OBJECT-TYPE
    SYNTAX  INTEGER(1..10000000)
            MAX-ACCESS  read-write
            STATUS  current
            DESCRIPTION
                "CIR(Committed Information Rate) Kbits per second <1-10000000>"
            ::= { qos3AggregatePolicyEntry 2 }

--xxx.100.11.2.3.1.3
qos3AggPolicyCBSKbps OBJECT-TYPE
    SYNTAX  INTEGER(1..1000000)
            MAX-ACCESS  read-write
            STATUS  current
            DESCRIPTION
                "CBS(Committed Burst Size) Kbytes  <1-1000000>"
            ::= { qos3AggregatePolicyEntry 3 }
            
--xxx.100.11.2.3.1.4
qos3AggPolicyPBSKbps OBJECT-TYPE
    SYNTAX  INTEGER(1..1000000)
            MAX-ACCESS  read-write
            STATUS  current
            DESCRIPTION
                "PBS(Peak Burst Size) Kbytes <1-1000000>"
            ::= { qos3AggregatePolicyEntry 4 }

--xxx.100.11.2.3.1.5
qos3AggPolicyPIRKbps OBJECT-TYPE
    SYNTAX  INTEGER(1..10000000)
            MAX-ACCESS  read-write
            STATUS  current
            DESCRIPTION
                "PIR(Peak Information Rate) Kbits per second <1-10000000>"
            ::= { qos3AggregatePolicyEntry 5 }
            
--xxx.100.11.2.3.1.6
qos3AggPolicyConformAction OBJECT-TYPE
    SYNTAX  BITS
            {
               transmit(0),
               drop(1),
               cos(2),
               dscp(3),
               ipPrecedence(4),
               intp(5),
               dp(6)
            }
            MAX-ACCESS  read-write
            STATUS  current
            DESCRIPTION
                "Action when rate is not exceeded,for example: if you want to config cos(2) and intp(5),you must set 24 (0010 0100)."
            ::= { qos3AggregatePolicyEntry 6 }
            
--xxx.100.11.2.3.1.7
qos3AggPolicyconformSetCos OBJECT-TYPE
    SYNTAX  INTEGER(0..7)
            MAX-ACCESS  read-write
            STATUS  current
            DESCRIPTION
                "Set COS"
            ::= { qos3AggregatePolicyEntry 7 }
            
--xxx.100.11.2.3.1.8
qos3AggPolicyconformSetDscp OBJECT-TYPE
    SYNTAX  INTEGER(0..63)
            MAX-ACCESS  read-write
            STATUS  current
            DESCRIPTION
                "Change dscp"
            ::= { qos3AggregatePolicyEntry 8 }
            
--xxx.100.11.2.3.1.9
qos3AggPolicyconformSetPrec OBJECT-TYPE
    SYNTAX  INTEGER(0..7)
            MAX-ACCESS  read-write
            STATUS  current
            DESCRIPTION
                "Change precedence"
            ::= { qos3AggregatePolicyEntry 9 }
            
--xxx.100.11.2.3.1.10
qos3AggPolicyconformSetIntp OBJECT-TYPE
    SYNTAX  INTEGER(0..7)
            MAX-ACCESS  read-write
            STATUS  current
            DESCRIPTION
                "Set Internal priority"
            ::= { qos3AggregatePolicyEntry 10 }
            
--xxx.100.11.2.3.1.11
qos3AggPolicyconformSetDp OBJECT-TYPE
    SYNTAX  INTEGER(0..2)
            MAX-ACCESS  read-write
            STATUS  current
            DESCRIPTION
                "Set Drop priority"
            ::= { qos3AggregatePolicyEntry 11 }
            
--xxx.100.11.2.3.1.12
qos3AggPolicyExceedAction OBJECT-TYPE
    SYNTAX  BITS
            {  
               transmit(0),        
               drop(1),
               cos(2),
               dscp(3),
               ipPrecedence(4),
               intp(5),
               dp(6),
               policiedIntpTransmit(7)
            }
            MAX-ACCESS  read-write
            STATUS  current
            DESCRIPTION
                "Action when rate is exceeded,for example: if you want to config cos(2) and intp(5),you must set 24 (0010 0100)."
            ::= { qos3AggregatePolicyEntry 12 }
            
--xxx.100.11.2.3.1.13
qos3AggPolicyExceedSetCos OBJECT-TYPE
    SYNTAX  INTEGER(0..7)
            MAX-ACCESS  read-write
            STATUS  current
            DESCRIPTION
                "Set COS"
            ::= { qos3AggregatePolicyEntry 13 }
            
--xxx.100.11.2.3.1.14
qos3AggPolicyExceedSetDscp OBJECT-TYPE
    SYNTAX  INTEGER(0..63)
            MAX-ACCESS  read-write
            STATUS  current
            DESCRIPTION
                " Change dscp"
            ::= { qos3AggregatePolicyEntry 14 }
            
--xxx.100.11.2.3.1.15
qos3AggPolicyExceedSetPrec OBJECT-TYPE
    SYNTAX  INTEGER(0..7)
            MAX-ACCESS  read-write
            STATUS  current
            DESCRIPTION
                "Change precedence"
            ::= { qos3AggregatePolicyEntry 15 }
            
--xxx.100.11.2.3.1.16
qos3AggPolicyExceedSetIntp OBJECT-TYPE
    SYNTAX  INTEGER(0..7)
            MAX-ACCESS  read-write
            STATUS  current
            DESCRIPTION
                "Set Internal priority"
            ::= { qos3AggregatePolicyEntry 16 }
            
--xxx.100.11.2.3.1.17
qos3AggPolicyExceedSetDp OBJECT-TYPE
    SYNTAX  INTEGER(0..2)
            MAX-ACCESS  read-write
            STATUS  current
            DESCRIPTION
                "Set Drop priority"
            ::= { qos3AggregatePolicyEntry 17 }
            
--xxx.100.11.2.3.1.18
qos3AggPolicyViolateAction OBJECT-TYPE
    SYNTAX  BITS
            {  
               transmit(0),        
               drop(1),
               cos(2),
               dscp(3),
               ipPrecedence(4),
               intp(5),
               dp(6),
               policiedIntpTransmit(7)
            }
            MAX-ACCESS  read-write
            STATUS  current
            DESCRIPTION
                "Action when rate is violated,for example: if you want to config cos(2) and intp(5),you must set 24 (0010 0100)."
            ::= { qos3AggregatePolicyEntry 18 }
            
--xxx.100.11.2.3.1.19
qos3AggPolicyViolateSetCos OBJECT-TYPE
    SYNTAX  INTEGER(0..7)
            MAX-ACCESS  read-write
            STATUS  current
            DESCRIPTION
                "Set COS"
            ::= { qos3AggregatePolicyEntry 19 }

--xxx.100.11.2.3.1.20
qos3AggPolicyViolateSetDscp OBJECT-TYPE
    SYNTAX  INTEGER(0..63)
            MAX-ACCESS  read-write
            STATUS  current
            DESCRIPTION
                "Change dscp"
            ::= { qos3AggregatePolicyEntry 20 }
            
--xxx.100.11.2.3.1.21
qos3AggPolicyViolateSetPrec OBJECT-TYPE
    SYNTAX  INTEGER(0..7  )
            MAX-ACCESS  read-write
            STATUS  current
            DESCRIPTION
                "Change precedence"
            ::= { qos3AggregatePolicyEntry 21 }
            
--xxx.100.11.2.3.1.22
qos3AggPolicyViolateSetIntp OBJECT-TYPE
    SYNTAX  INTEGER(0..7)
            MAX-ACCESS  read-write
            STATUS  current
            DESCRIPTION
                "Set Internal priority"
            ::= { qos3AggregatePolicyEntry 22 }
            
--xxx.100.11.2.3.1.23
qos3AggPolicyViolateSetDp OBJECT-TYPE
    SYNTAX  INTEGER(0..2)
            MAX-ACCESS  read-write
            STATUS  current
            DESCRIPTION
                "Set Drop priority"
            ::= { qos3AggregatePolicyEntry 23 }
            
--xxx.100.11.2.3.1.24
qos3AggPolicyStatus OBJECT-TYPE
    SYNTAX  INTEGER
            {
              createAndGo(0),
              active(1),
              destroy(2)
            }
            MAX-ACCESS  read-write
            STATUS  current
            DESCRIPTION
                "the status of qos3AggregatePolicyTable"
            ::= { qos3AggregatePolicyEntry 24 }

--********************************************************************************************************
--xxx.100.11.2.4
qos3PolicyTable OBJECT-TYPE
    SYNTAX  SEQUENCE OF Qos3PolicyEntry
    MAX-ACCESS  not-accessible
    STATUS  current
            DESCRIPTION
                "this table is used for configuring policy"
            ::= { qos3 4 } 

--xxx.100.11.2.4.1
    qos3PolicyEntry OBJECT-TYPE
        SYNTAX  Qos3PolicyEntry
        MAX-ACCESS  not-accessible
        STATUS  current
        DESCRIPTION
            "entry for policy."
        INDEX   { qos3PolicyMapIndex,  qos3PolicyClassMapName }
        ::= { qos3PolicyTable 1 } 

    Qos3PolicyEntry
        ::= SEQUENCE
            {
                qos3PolicyMapIndex                 INTEGER,
                qos3PolicyClassMapName			       DisplayString,
                qos3PolicyInsertClassMapName       DisplayString,
                qos3PolicyType                      BITS,
                qos3PolicyCIRKbps			         INTEGER,
                qos3PolicyCBSKbps               INTEGER,                
                qos3PolicyPBSKbps			         INTEGER,
                qos3PolicyPIRKbps               INTEGER,
                qos3PolicyConformAction	       BITS,
                qos3PolicyconformSetCos         INTEGER,
                qos3PolicyconformSetDscp        INTEGER,
                qos3PolicyconformSetPrec        INTEGER,
                qos3PolicyconformSetIntp        INTEGER,
                qos3PolicyconformSetDp          INTEGER,
                qos3PolicyExceedAction          BITS,
                qos3PolicyExceedSetCos          INTEGER,
                qos3PolicyExceedSetDscp         INTEGER,
                qos3PolicyExceedSetPrec         INTEGER,
                qos3PolicyExceedSetIntp         INTEGER,
                qos3PolicyExceedSetDp           INTEGER,
                qos3PolicyViolateAction         BITS,
                qos3PolicyViolateSetCos         INTEGER,
                qos3PolicyViolateSetDscp        INTEGER,
                qos3PolicyViolateSetPrec        INTEGER,
                qos3PolicyViolateSetIntp        INTEGER,
                qos3PolicyViolateSetDp          INTEGER,
                qos3PolicyAggregatePolicer      DisplayString,
                qos3PolicyAccounting            INTEGER,
                qos3PolicyPidAction             BITS,
                qos3SetCos                      INTEGER,
                qos3SetIpDscp                   INTEGER,
                qos3SetIpPrec                    INTEGER,
                qos3SetIntp                     INTEGER,
                qos3SetDp                       INTEGER,
                qos3SetCVid                      INTEGER,
                qos3SetSVid                      INTEGER,
                qos3SetSTpid                    INTEGER,
                qos3AddSVid                     INTEGER,
                qos3DelCVid                     INTEGER, 
                qos3SetTunnelId                 INTEGER,                                  
                qos3SetIpDefaultPBR               INTEGER,
                qos3SetIpVrf                       INTEGER,
                qos3SetIpNextHop                IpAddress,
                qos3SetExp                      INTEGER,
                qos3SetIpv6DefaultPBR               INTEGER,
                qos3SetIpv6Vrf                       INTEGER,
                qos3SetIpv6NextHop              DisplayString,                                   
                qos3PolicyStatus                INTEGER
    
            }

--xxx.100.11.2.4.1.1
qos3PolicyMapIndex OBJECT-TYPE
    SYNTAX  INTEGER
            MAX-ACCESS  read-only
            STATUS  current
            DESCRIPTION
                "the index of policy that you configured at qos3PolicyMapGroupTable"
            ::= { qos3PolicyEntry 1 }
            
--xxx.100.11.2.4.1.2
qos3PolicyClassMapName OBJECT-TYPE
    SYNTAX  DisplayString(SIZE(1..64))
            MAX-ACCESS  read-only
            STATUS  current
            DESCRIPTION
                "Specify the classmap name.After a policy map is created, it can be associated to a class"
            ::= { qos3PolicyEntry 2 }            

--xxx.100.11.2.4.1.3
qos3PolicyInsertClassMapName OBJECT-TYPE
    SYNTAX  DisplayString(SIZE(1..64))
            MAX-ACCESS  read-write
            STATUS  current
            DESCRIPTION
                "Specify the position of classmap name"
            ::= { qos3PolicyEntry 3 }   

--xxx.100.11.2.4.1.4
qos3PolicyType OBJECT-TYPE
    SYNTAX  BITS
            {
              pidAction(0),
              colorAction(1),
              aggregateAction(2)
            }
            MAX-ACCESS  read-write
            STATUS  current
            DESCRIPTION
                "pidAction means simple policy.colorAction and aggregateAction is Mutually exclusive,for example,if you 
                want the pidAction and colorAction become effective,you must set the value c0."
            ::= { qos3PolicyEntry 4 } 
                        
--xxx.100.11.2.4.1.5
qos3PolicyCIRKbps OBJECT-TYPE
    SYNTAX  INTEGER(1..10000000)
            MAX-ACCESS  read-write
            STATUS  current
            DESCRIPTION
                "CIR(Committed Information Rate) Kbits per second <1-10000000>"
            ::= { qos3PolicyEntry 5 }

--xxx.100.11.2.4.1.6
qos3PolicyCBSKbps OBJECT-TYPE
    SYNTAX  INTEGER(1..1000000)
            MAX-ACCESS  read-write
            STATUS  current
            DESCRIPTION
                " CBS(Committed Burst Size) Kbytes  <1-1000000>"
            ::= { qos3PolicyEntry 6 }
            
--xxx.100.11.2.4.1.7
qos3PolicyPBSKbps OBJECT-TYPE
    SYNTAX  INTEGER(1..1000000)
            MAX-ACCESS  read-write
            STATUS  current
            DESCRIPTION
                " PBS(Peak Burst Size) Kbytes <1-1000000>"
            ::= { qos3PolicyEntry 7 }

--xxx.100.11.2.4.1.8
qos3PolicyPIRKbps OBJECT-TYPE
    SYNTAX  INTEGER(1..10000000)
            MAX-ACCESS  read-write
            STATUS  current
            DESCRIPTION
                "PIR(Peak Information Rate) Kbits per second <1-10000000>"
            ::= { qos3PolicyEntry 8 }
            
--xxx.100.11.2.4.1.9
qos3PolicyConformAction OBJECT-TYPE
    SYNTAX  BITS
            {  
               transmit(0),        
               drop(1),
               cos(2),
               dscp(3),
               ipPrecedence(4),
               intp(5),
               dp(6)
            }
            MAX-ACCESS  read-write
            STATUS  current
            DESCRIPTION
                "Action when rate is not exceeded,for example: if you want to config cos(2) and intp(5),you must set 24 (0010 0100)."
            ::= { qos3PolicyEntry 9 }
            
--xxx.100.11.2.4.1.10
qos3PolicyconformSetCos OBJECT-TYPE
    SYNTAX  INTEGER(0..7)
            MAX-ACCESS  read-write
            STATUS  current
            DESCRIPTION
                "Set COS"
            ::= { qos3PolicyEntry 10 }
            
--xxx.100.11.2.4.1.11
qos3PolicyconformSetDscp OBJECT-TYPE
    SYNTAX  INTEGER(0..63)
            MAX-ACCESS  read-write
            STATUS  current
            DESCRIPTION
                "Change dscp"
            ::= { qos3PolicyEntry 11 }
            
--xxx.100.11.2.4.1.12
qos3PolicyconformSetPrec OBJECT-TYPE
    SYNTAX  INTEGER(0..7)
            MAX-ACCESS  read-write
            STATUS  current
            DESCRIPTION
                "Change precedence"
            ::= { qos3PolicyEntry 12 }
            
--xxx.100.11.2.4.1.13
qos3PolicyconformSetIntp OBJECT-TYPE
    SYNTAX  INTEGER(0..7)
            MAX-ACCESS  read-write
            STATUS  current
            DESCRIPTION
                "Set Internal priority"
            ::= { qos3PolicyEntry 13 }
            
--xxx.100.11.2.4.1.14
qos3PolicyconformSetDp OBJECT-TYPE
    SYNTAX  INTEGER(0..2)
            MAX-ACCESS  read-write
            STATUS  current
            DESCRIPTION
                "Set Drop priority"
            ::= { qos3PolicyEntry 14 }
            
--xxx.100.11.2.4.1.15
qos3PolicyExceedAction OBJECT-TYPE
    SYNTAX  BITS
            {  
               transmit(0),        
               drop(1),
               cos(2),
               dscp(3),
               ipPrecedence(4),
               intp(5),
               dp(6), 
               policiedIntpTransmit(7)
            }
            MAX-ACCESS  read-write
            STATUS  current
            DESCRIPTION
                "Action when rate is exceeded,for example: if you want to config cos(2) and intp(5),you must set 24 (0010 0100)."
            ::= { qos3PolicyEntry 15 }
            
--xxx.100.11.2.3.1.16
qos3PolicyExceedSetCos OBJECT-TYPE
    SYNTAX  INTEGER(0..7)
            MAX-ACCESS  read-write
            STATUS  current
            DESCRIPTION
                "Set COS"
            ::= { qos3PolicyEntry 16 }
            
--xxx.100.11.2.4.1.17
qos3PolicyExceedSetDscp OBJECT-TYPE
    SYNTAX  INTEGER(0..63)
            MAX-ACCESS  read-write
            STATUS  current
            DESCRIPTION
                "Change dscp"
            ::= { qos3PolicyEntry 17 }
            
--xxx.100.11.2.3.1.18
qos3PolicyExceedSetPrec OBJECT-TYPE
    SYNTAX  INTEGER(0..7)
            MAX-ACCESS  read-write
            STATUS  current
            DESCRIPTION
                "Change precedence"
            ::= { qos3PolicyEntry 18 }
            
--xxx.100.11.2.3.1.19
qos3PolicyExceedSetIntp OBJECT-TYPE
    SYNTAX  INTEGER(0..7)
            MAX-ACCESS  read-write
            STATUS  current
            DESCRIPTION
                "Set Internal priority"
            ::= { qos3PolicyEntry 19 }
            
--xxx.100.11.2.4.1.20
qos3PolicyExceedSetDp OBJECT-TYPE
    SYNTAX  INTEGER(0..2)
            MAX-ACCESS  read-write
            STATUS  current
            DESCRIPTION
                "Set Drop priority"
            ::= { qos3PolicyEntry 20 }
            
--xxx.100.11.2.4.1.21
qos3PolicyViolateAction OBJECT-TYPE
    SYNTAX  BITS
            {  
               transmit(0),        
               drop(1),
               cos(2),
               dscp(3),
               ipPrecedence(4),
               intp(5),
               dp(6),
               policiedIntpTransmit(7)
            }
            MAX-ACCESS  read-write
            STATUS  current
            DESCRIPTION
                "Action when rate is violated,for example: if you want to config cos(2) and intp(5),you must set 24 (0010 0100)."
            ::= { qos3PolicyEntry 21 }
            
--xxx.100.11.2.3.1.22
qos3PolicyViolateSetCos OBJECT-TYPE
    SYNTAX  INTEGER(0..7)
            MAX-ACCESS  read-write
            STATUS  current
            DESCRIPTION
                " Set COS"
            ::= { qos3PolicyEntry 22 }

--xxx.100.11.2.3.1.23
qos3PolicyViolateSetDscp OBJECT-TYPE
    SYNTAX  INTEGER(0..63)
            MAX-ACCESS  read-write
            STATUS  current
            DESCRIPTION
                "Change dscp"
            ::= { qos3PolicyEntry 23 }
            
--xxx.100.11.2.3.1.24
qos3PolicyViolateSetPrec OBJECT-TYPE
    SYNTAX  INTEGER(0..7)
            MAX-ACCESS  read-write
            STATUS  current
            DESCRIPTION
                "Change precedence"
            ::= { qos3PolicyEntry 24 }
            
--xxx.100.11.2.3.1.25
qos3PolicyViolateSetIntp OBJECT-TYPE
    SYNTAX  INTEGER(0..7)
            MAX-ACCESS  read-write
            STATUS  current
            DESCRIPTION
                "Set Internal priority"
            ::= { qos3PolicyEntry 25 }
            
--xxx.100.11.2.3.1.26
qos3PolicyViolateSetDp OBJECT-TYPE
    SYNTAX  INTEGER(0..2)
            MAX-ACCESS  read-write
            STATUS  current
            DESCRIPTION
                "Set Drop priority"
            ::= { qos3PolicyEntry 26 }

--xxx.100.11.2.3.1.26
qos3PolicyAggregatePolicer OBJECT-TYPE
    SYNTAX  DisplayString
            MAX-ACCESS  read-write
            STATUS  current
            DESCRIPTION
                "the name of aggregate policy"
            ::= { qos3PolicyEntry 27 }

--xxx.100.11.2.3.1.28
qos3PolicyAccounting OBJECT-TYPE
    SYNTAX  INTEGER
            {
              disable(0),
              enable(1)
            }
            MAX-ACCESS  read-write
            STATUS  current
            DESCRIPTION
                "enable the Counter statistics or not."
            ::= { qos3PolicyEntry 28 }

--xxx.100.11.2.3.1.26
qos3PolicyPidAction OBJECT-TYPE
    SYNTAX  BITS
            {
              cos(0),
              dscp(1),
              ipPrecedence(2),
              ipNextHop(3),
              exp(4),
              ipv6NextHop(5),              
              intp(6),
              dp(7),
              setCvid(8),
              setSvid(9),
              setSTpid(10),
              addSvid(11),
              delCvid(12),
              setTunnelId(13),
              transmit(14),
              drop(15)              
            }
            MAX-ACCESS  read-write
            STATUS  current
            DESCRIPTION
                "simple policy action,for example: if you want to config cos(0) and setSTpid(10),you must set 8020 (1000 0000 0010 0000).
                some network Management Software offer selections that is not correct,in RFC3417,When encoding an object whose syntax is 
                described using the BITS construct, the value is encoded as an OCTET STRING, in which all the named bits in (the definition of) the bitstring,
								commencing with the first bit and proceeding to the last bit,are placed in bits 8 (high order bit) to 1 (low order bit) of
								the first octet, followed by bits 8 to 1 of each subsequent octet in turn, followed by as many bits as are needed of the
								final subsequent octet, commencing with bit 8. Remaining bits,if any, of the final octet are set to zero on generation and
								ignored on receipt."
            ::= { qos3PolicyEntry 29 }
            
--xxx.100.11.2.3.1.26
qos3SetCos OBJECT-TYPE
    SYNTAX  INTEGER(0..7)
            MAX-ACCESS  read-write
            STATUS  current
            DESCRIPTION
                "set cos"
            ::= { qos3PolicyEntry 30 }
            
--xxx.100.11.2.3.1.26
qos3SetIpDscp OBJECT-TYPE
    SYNTAX  INTEGER(0..63)
            MAX-ACCESS  read-write
            STATUS  current
            DESCRIPTION
                "change dscp"
            ::= { qos3PolicyEntry 31 }

--xxx.100.11.2.3.1.26
qos3SetIpPrec OBJECT-TYPE
    SYNTAX  INTEGER(0..7)
            MAX-ACCESS  read-write
            STATUS  current
            DESCRIPTION
                "change precedence"
            ::= { qos3PolicyEntry 32 }
            
--xxx.100.11.2.3.1.26
qos3SetIntp OBJECT-TYPE
    SYNTAX  INTEGER(0..7)
            MAX-ACCESS  read-write
            STATUS  current
            DESCRIPTION
                " Set Internal priority"
            ::= { qos3PolicyEntry 33 }
            
--xxx.100.11.2.3.1.26
qos3SetDp OBJECT-TYPE
    SYNTAX  INTEGER(0..2)
            MAX-ACCESS  read-write
            STATUS  current
            DESCRIPTION
                "Set Drop priority"
            ::= { qos3PolicyEntry 34 }
            
--xxx.100.11.2.3.1.26
qos3SetCVid OBJECT-TYPE
    SYNTAX  INTEGER(1..4094)
            MAX-ACCESS  read-write
            STATUS  current
            DESCRIPTION
                "set  vlan id of inner VLAN tag."
            ::= { qos3PolicyEntry 35 }
            

            
--xxx.100.11.2.3.1.26
qos3SetSVid OBJECT-TYPE
    SYNTAX  INTEGER(1..4094)
            MAX-ACCESS  read-write
            STATUS  current
            DESCRIPTION
                "set vlan id of outer VLAN tag."
            ::= { qos3PolicyEntry 36 }
            
            
--xxx.100.11.2.3.1.26
qos3SetSTpid OBJECT-TYPE
    SYNTAX  INTEGER
            {
              value0x8100(1),
              value0x88a8(2),
              value0x9100(3)
            }
            MAX-ACCESS  read-write
            STATUS  current
            DESCRIPTION
                "Set S-tpid"
            ::= { qos3PolicyEntry 37 }
--xxx.100.11.2.3.1.26
qos3AddSVid OBJECT-TYPE
    SYNTAX  INTEGER(1..4094)
            MAX-ACCESS  read-write
            STATUS  current
            DESCRIPTION
                "add vlan id of outer VLAN tag"
            ::= { qos3PolicyEntry 38 }
            
--xxx.100.11.2.3.1.26
qos3DelCVid OBJECT-TYPE
    SYNTAX  INTEGER
            {
               disable(0),
               enable(1)
            }
            MAX-ACCESS  read-only
            STATUS  current
            DESCRIPTION
                "delete vlan id of inner VLAN tag."
            ::= { qos3PolicyEntry 39 }
            
--xxx.100.11.2.3.1.26
qos3SetTunnelId OBJECT-TYPE
    SYNTAX  INTEGER(1..50)
            MAX-ACCESS  read-write
            STATUS  current
            DESCRIPTION
                ""
            ::= { qos3PolicyEntry 40 }            
                        
--xxx.100.11.2.3.1.26
qos3SetIpDefaultPBR OBJECT-TYPE
    SYNTAX  INTEGER
            {
               disable(0),
               enable(1)
            }
            MAX-ACCESS  read-write
            STATUS  current
            DESCRIPTION
                "whether add Default routing of ip type."
            ::= { qos3PolicyEntry 41 }

--xxx.100.11.2.3.1.26
qos3SetIpVrf OBJECT-TYPE
    SYNTAX  INTEGER(0..252)
            MAX-ACCESS  read-write
            STATUS  current
            DESCRIPTION
                "set the vrf of ip type"
            ::= { qos3PolicyEntry 42 }
                        
--xxx.100.11.2.3.1.26
qos3SetIpNextHop OBJECT-TYPE
    SYNTAX  IpAddress
            MAX-ACCESS  read-write
            STATUS  current
            DESCRIPTION
                "set Nexthop IP address."
            ::= { qos3PolicyEntry 43 }
            
--xxx.100.11.2.3.1.26
qos3SetExp OBJECT-TYPE
    SYNTAX  INTEGER(0..7)
            MAX-ACCESS  read-write
            STATUS  current
            DESCRIPTION
                "set exp."
            ::= { qos3PolicyEntry 44 }

--xxx.100.11.2.3.1.26
qos3SetIpv6DefaultPBR OBJECT-TYPE
    SYNTAX  INTEGER
            {
               disable(0),
               enable(1)
            }
            MAX-ACCESS  read-write
            STATUS  current
            DESCRIPTION
                "whether add Default routing of ipv6 type "
            ::= { qos3PolicyEntry 45 }

--xxx.100.11.2.3.1.26
qos3SetIpv6Vrf OBJECT-TYPE
    SYNTAX  INTEGER(0..252)
            MAX-ACCESS  read-write
            STATUS  current
            DESCRIPTION
                "set the vrf of ipv6 type."
            ::= { qos3PolicyEntry 46 }
                        
--xxx.100.11.2.3.1.26
qos3SetIpv6NextHop OBJECT-TYPE
    SYNTAX  DisplayString(SIZE(1..40))
            MAX-ACCESS  read-write
            STATUS  current
            DESCRIPTION
                "set Nexthop IPv6 address"
            ::= { qos3PolicyEntry 47 }
                                                                                                                                                                                                                                                                              
--xxx.100.11.2.3.1.44
qos3PolicyStatus OBJECT-TYPE
    SYNTAX  INTEGER
            {
              createAndGo(0),
              active(1),
              destroy(2),
              removeColorAct(3),
              removeAggregateAct(4),
              removePidAct(5)
            }
            MAX-ACCESS  read-write
            STATUS  current
            DESCRIPTION
                "the status of qos3PolicyTable. destroy(2) will put off the class-map,removeColorAct(3) will clear the color-act,
                 removeAggregateAct(4) will clear the aggregate-act,removePidAct(5) will clear the value while you set int pidAction."            
            ::= { qos3PolicyEntry 48 }

--*******************************************************************************************************************************************

--xxx.100.11.2.5
qos3PortTable OBJECT-TYPE 
    SYNTAX  SEQUENCE OF Qos3PortEntry
    MAX-ACCESS  not-accessible
    STATUS  current
    DESCRIPTION
        "qos port configration."
    ::= { qos3   5 }
            
--xxx.100.11.2.5.1
qos3PortEntry OBJECT-TYPE
        SYNTAX  Qos3PortEntry
        MAX-ACCESS  not-accessible
        STATUS  current
        DESCRIPTION
            "entry for port configuration of qos about trust,cos value,queue drop-algorithm and queue algorithm."
        INDEX   { qos3PortIndex }
        ::= { qos3PortTable 1 }

Qos3PortEntry
        ::= SEQUENCE
            {
                qos3PortIndex            INTEGER,
                qos3PortCos		           INTEGER,
                qos3PortTrust	           BITS,
                qos3PortWredEnable       INTEGER,
                qos3PortQueueAlgorithm      INTEGER,
                qos3PortPassThroughCos      INTEGER,
                qos3PortPassThroughDscp     INTEGER
            }
            
--xxx.100.11.2.5.1.1       
qos3PortIndex   OBJECT-TYPE
	SYNTAX      INTEGER 
        MAX-ACCESS  read-only
        STATUS      current
        DESCRIPTION 
          "port index."
        ::= { qos3PortEntry 1 } 

--xxx.100.11.2.5.1.2       
qos3PortCos   OBJECT-TYPE
	SYNTAX      INTEGER(0..7) 
        MAX-ACCESS  read-write
        STATUS      current
        DESCRIPTION 
           "set default cos of the port."
        ::= { qos3PortEntry 2 }

--xxx.100.11.2.5.1.3       
qos3PortTrust   OBJECT-TYPE
	SYNTAX      BITS
	            {
	             cosEnable(0),
	             dscpEnable(1),
	             expEnable(2),
	             cosDisable(3),
	             dscpDisable(4),
	             expDisbable(5)
	            } 
        MAX-ACCESS  read-write
        STATUS      current
        DESCRIPTION 
          "set port trust. cosEnable,dscpEnable and expEnable can be set at the same time;cosDisable,dscpDisable and expDisbable can be set at the same time;
          cosEnable,dscpEnable and expEnable can not be set at the same time with dscpDisable,cosDisable and expDisbable."
        ::= { qos3PortEntry 3 }

--xxx.100.11.2.5.1.4      
qos3PortWredEnable   OBJECT-TYPE
	SYNTAX      INTEGER
	            {
	              tail(0),
	              wred(1)
	            } 
        MAX-ACCESS  read-write
        STATUS      current
        DESCRIPTION 
          "set the drop Algorithm of port's queue."
        ::= { qos3PortEntry 4 }
        
--xxx.100.11.2.5.1.5     
qos3PortQueueAlgorithm   OBJECT-TYPE
	SYNTAX      INTEGER
	            {
	              sp(0),
	              wrr(1),
	              wdrr(2)
	            } 
        MAX-ACCESS  read-write
        STATUS      current
        DESCRIPTION 
           " effected the weight Algorithm of port's queue."
        ::= { qos3PortEntry 5 }
        
qos3PortPassThroughCos   OBJECT-TYPE
	SYNTAX      INTEGER
	            {
	              disable(0),
	              enable(1)
	            } 
        MAX-ACCESS  read-write
        STATUS      current
        DESCRIPTION 
           " forbid changing the value of cos."
        ::= { qos3PortEntry 6 }
        
qos3PortPassThroughDscp   OBJECT-TYPE
	SYNTAX      INTEGER
	            {
	              disable(0),
	              enable(1)
	            } 
        MAX-ACCESS  read-write
        STATUS      current
        DESCRIPTION 
           " forbid changing the value of dscp."
        ::= { qos3PortEntry 7 }               

--********************************************************************************************************
--xxx.100.11.2.6
qos3QueueWeightTable OBJECT-TYPE 
    SYNTAX  SEQUENCE OF Qos3QueueWeightEntry
    MAX-ACCESS  not-accessible
    STATUS  current
    DESCRIPTION
        "this table is used for configuring port's weight"
    ::= { qos3   6}
            
--xxx.100.11.2.6.1
qos3QueueWeightEntry OBJECT-TYPE
        SYNTAX  Qos3QueueWeightEntry
        MAX-ACCESS  not-accessible
        STATUS  current
        DESCRIPTION
            "entry for queue weight configuration."
        INDEX   { qos3QueueWeightPortIndex,qos3QueueWeightType }
        ::= { qos3QueueWeightTable 1 }

Qos3QueueWeightEntry
        ::= SEQUENCE
            {
                qos3QueueWeightPortIndex        INTEGER,
                qos3QueueWeightType		          INTEGER,
                qos3QueueWeight0	              INTEGER,
                qos3QueueWeight1                INTEGER,
                qos3QueueWeight2                INTEGER,
                qos3QueueWeight3                INTEGER,
                qos3QueueWeight4                INTEGER,
                qos3QueueWeight5                INTEGER,
                qos3QueueWeight6                INTEGER,
                qos3QueueWeight7                INTEGER,
                qos3QueueWeightStatus           INTEGER
            }
            
--xxx.100.11.2.6.1.1       
qos3QueueWeightPortIndex   OBJECT-TYPE
	SYNTAX      INTEGER 
        MAX-ACCESS  read-only
        STATUS      current
        DESCRIPTION 
          "port index."
        ::= { qos3QueueWeightEntry 1 } 

--xxx.100.11.2.6.1.2       
qos3QueueWeightType   OBJECT-TYPE
	SYNTAX      INTEGER
	            {
	              wrr(0),
	              wdrr(1)
	            } 
        MAX-ACCESS  read-only
        STATUS      current
        DESCRIPTION 
          "choose the algorithm weight that you want to set."
        ::= { qos3QueueWeightEntry 2 } 
        
        
--xxx.100.11.2.6.1.3     
qos3QueueWeight0   OBJECT-TYPE
	SYNTAX      INTEGER(0..32767) 
        MAX-ACCESS  read-write
        STATUS      current
        DESCRIPTION 
          "wrr default value is 1,wdrr default value is 10."
        ::= { qos3QueueWeightEntry 3 } 


--xxx.100.11.2.6.1.4   
qos3QueueWeight1   OBJECT-TYPE
	SYNTAX      INTEGER(0..32767)  
        MAX-ACCESS  read-write
        STATUS      current
        DESCRIPTION 
          "wrr default value is 2,wdrr default value is 20"
        ::= { qos3QueueWeightEntry 4 } 
        
--xxx.100.11.2.6.1.5    
qos3QueueWeight2   OBJECT-TYPE
	SYNTAX      INTEGER(0..32767)   
        MAX-ACCESS  read-write
        STATUS      current
        DESCRIPTION 
          "wrr default value is 3,wdrr default value is 40"
        ::= { qos3QueueWeightEntry 5 } 
        
--xxx.100.11.2.6.1.6   
qos3QueueWeight3   OBJECT-TYPE
	SYNTAX      INTEGER(0..32767)  
        MAX-ACCESS  read-write
        STATUS      current
        DESCRIPTION 
         "wrr default value is 4,wdrr default value is 80"
        ::= { qos3QueueWeightEntry 6 } 
        
--xxx.100.11.2.6.1.7    
qos3QueueWeight4   OBJECT-TYPE
	SYNTAX      INTEGER(0..32767)   
        MAX-ACCESS  read-write
        STATUS      current
        DESCRIPTION 
          "wrr default value is 5,wdrr default value is 160"
        ::= { qos3QueueWeightEntry 7 } 
        
--xxx.100.11.2.6.1.8    
qos3QueueWeight5   OBJECT-TYPE
	SYNTAX      INTEGER(0..32767)  
        MAX-ACCESS  read-write
        STATUS      current
        DESCRIPTION 
          "wrr default value is 6,wdrr default value is 320"
        ::= { qos3QueueWeightEntry 8 } 
        
--xxx.100.11.2.6.1.9     
qos3QueueWeight6   OBJECT-TYPE
	SYNTAX      INTEGER(0..32767)  
        MAX-ACCESS  read-write
        STATUS      current
        DESCRIPTION 
          "wrr default value is 7,wdrr default value is 640"
        ::= { qos3QueueWeightEntry 9 } 
        
--xxx.100.11.2.6.1.10    
qos3QueueWeight7   OBJECT-TYPE
	SYNTAX      INTEGER(0..32767)  
        MAX-ACCESS  read-write
        STATUS      current
        DESCRIPTION 
          "wrr default value is 8,wdrr default value is 1280"
        ::= { qos3QueueWeightEntry 10 } 
        
--xxx.100.11.2.6.1.11    
qos3QueueWeightStatus   OBJECT-TYPE
	SYNTAX      INTEGER 
		            {
	              createAndGo(0),
	              active(1),
	              destroy(2)
	            }
        MAX-ACCESS  read-write
        STATUS      current
        DESCRIPTION 
          "the status of qos3QueueWeightTable."
        ::= { qos3QueueWeightEntry 11 } 
        
--********************************************************************************************************

--xxx.100.11.2.7
qos3QueueBindWidthTable OBJECT-TYPE 
    SYNTAX  SEQUENCE OF Qos3QueueBindWidthEntry
    MAX-ACCESS  not-accessible
    STATUS  current
    DESCRIPTION
        "this table is used for setting bindwidth of port."
    ::= { qos3   7 }
            
--xxx.100.11.2.7.1
qos3QueueBindWidthEntry OBJECT-TYPE
        SYNTAX  Qos3QueueBindWidthEntry
        MAX-ACCESS  not-accessible
        STATUS  current
        DESCRIPTION
            "entry for Queue BindWidth configuration."
        INDEX   { qos3QueueBindWidthPortIndex,qos3QueueBindWidthQueueId }
        ::= { qos3QueueBindWidthTable 1 }

Qos3QueueBindWidthEntry
        ::= SEQUENCE
            {
                qos3QueueBindWidthPortIndex     INTEGER,
                qos3QueueBindWidthQueueId		    INTEGER,
                qos3QueueBindWidthMin	          INTEGER,
                qos3QueueBindWidthMax           INTEGER,
                qos3QueueBindWidthStatus        INTEGER
            }
            
--xxx.100.11.2.7.1.1       
qos3QueueBindWidthPortIndex   OBJECT-TYPE
	SYNTAX      INTEGER 
        MAX-ACCESS  read-only
        STATUS      current
        DESCRIPTION 
          "port index."
        ::= { qos3QueueBindWidthEntry 1 } 

--xxx.100.11.2.7.1.2     
qos3QueueBindWidthQueueId   OBJECT-TYPE
	SYNTAX      INTEGER(1..8) 
        MAX-ACCESS  read-only
        STATUS      current
        DESCRIPTION 
          "queue id"
        ::= { qos3QueueBindWidthEntry 2 } 

--xxx.100.11.2.7.1.3     
qos3QueueBindWidthMin   OBJECT-TYPE
	SYNTAX      INTEGER(0..128000)
        MAX-ACCESS  read-write
        STATUS      current
        DESCRIPTION 
          "the Smallest bindwidth."
        ::= { qos3QueueBindWidthEntry 3 }

--xxx.100.11.2.7.1.4     
qos3QueueBindWidthMax   OBJECT-TYPE
	SYNTAX      INTEGER(0..128000) 
        MAX-ACCESS  read-write
        STATUS      current
        DESCRIPTION 
          "the Largest bindwidth."
        ::= { qos3QueueBindWidthEntry 4 }
                        
--xxx.100.11.2.7.1.5     
qos3QueueBindWidthStatus   OBJECT-TYPE
	SYNTAX      INTEGER 
		            {
	              createAndGo(0),
	              active(1),
	              destroy(2)
	            }
        MAX-ACCESS  read-write
        STATUS      current
        DESCRIPTION 
         "the status of qos3QueueBindWidthTable"
        ::= { qos3QueueBindWidthEntry 5 }

--********************************************************************************************************
--xxx.100.11.2.8
qos3QueueWredTable OBJECT-TYPE 
    SYNTAX  SEQUENCE OF Qos3QueueWredEntry
    MAX-ACCESS  not-accessible
    STATUS  current
    DESCRIPTION
        "this table is used for configuring the drop Algorithm of queue"
    ::= { qos3   8 }
            
--xxx.100.11.2.8.1
qos3QueueWredEntry OBJECT-TYPE
        SYNTAX  Qos3QueueWredEntry
        MAX-ACCESS  not-accessible
        STATUS  current
        DESCRIPTION
            "entry for queue wred configuration."
        INDEX   { qos3QueueWredPortIndex,qos3QueueWredQueueId,qos3QueueWredDp}
        ::= { qos3QueueWredTable 1 }

Qos3QueueWredEntry
        ::= SEQUENCE
            {
                qos3QueueWredPortIndex      INTEGER,
                qos3QueueWredQueueId		    INTEGER,
                qos3QueueWredDp	            INTEGER,
                qos3QueueWredDpStart        INTEGER,
                qos3QueueWredDpEnd          INTEGER,
                qos3QueueWredDpMaxRate       INTEGER,
                qos3QueueWredStatus          INTEGER
            }
            
--xxx.100.11.2.8.1.1       
qos3QueueWredPortIndex   OBJECT-TYPE
	SYNTAX      INTEGER 
        MAX-ACCESS  read-only
        STATUS      current
        DESCRIPTION 
         "port index."
        ::= { qos3QueueWredEntry 1 } 

--xxx.100.11.2.8.1.2       
qos3QueueWredQueueId   OBJECT-TYPE
	SYNTAX      INTEGER(1..8) 
        MAX-ACCESS  read-only
        STATUS      current
        DESCRIPTION 
          "queue id."
        ::= { qos3QueueWredEntry 2 } 

--xxx.100.11.2.8.1.3       
qos3QueueWredDp   OBJECT-TYPE
	SYNTAX      INTEGER(0..2) 
        MAX-ACCESS  read-only
        STATUS      current
        DESCRIPTION 
          "drop Priority."
        ::= { qos3QueueWredEntry 3 } 

--xxx.100.11.2.8.1.4      
qos3QueueWredDpStart   OBJECT-TYPE
	SYNTAX      INTEGER(1..100) 
        MAX-ACCESS  read-write
        STATUS      current
        DESCRIPTION 
          "the smallist queue length when the queue start Discard packet."
        ::= { qos3QueueWredEntry 4 } 

--xxx.100.11.2.8.1.5     
qos3QueueWredDpEnd   OBJECT-TYPE
	SYNTAX      INTEGER(1..100) 
        MAX-ACCESS  read-write
        STATUS      current
        DESCRIPTION 
         "the Largest queue length when the queue start Discard packet"
        ::= { qos3QueueWredEntry 5 } 

--xxx.100.11.2.8.1.6    
qos3QueueWredDpMaxRate   OBJECT-TYPE
	SYNTAX      INTEGER(0..100) 
        MAX-ACCESS  read-write
        STATUS      current
        DESCRIPTION 
          "the max Discard Probability"
        ::= { qos3QueueWredEntry 6 } 

--xxx.100.11.2.8.1.7    
qos3QueueWredStatus   OBJECT-TYPE
	SYNTAX      INTEGER
	            {
	              createAndGo(0),
	              active(1),
	              destroy(2)
	            } 
        MAX-ACCESS  read-write
        STATUS      current
        DESCRIPTION 
         "the status of qos3QueueWredEntry"
        ::= { qos3QueueWredEntry 7 } 

--********************************************************************************************************
--xxx.100.11.2.9
qos3MapTable OBJECT-TYPE 
    SYNTAX  SEQUENCE OF Qos3MapEntry
    MAX-ACCESS  not-accessible
    STATUS  current
    DESCRIPTION
        "this table is used for setting map between priorities(eg:cos,intp)."
    ::= { qos3   9 }
            
--xxx.100.11.2.9.1
qos3MapEntry OBJECT-TYPE
        SYNTAX  Qos3MapEntry
        MAX-ACCESS  not-accessible
        STATUS  current
        DESCRIPTION
            "entry for mls qos map configuration."
        INDEX   { qos3MapType }
        ::= { qos3MapTable 1 }

Qos3MapEntry
        ::= SEQUENCE
            {
                qos3MapType          INTEGER,
                qos3MapAtoB1		     INTEGER,
                qos3MapAtoB2	       INTEGER,
                qos3MapAtoB3         INTEGER,
                qos3MapAtoB4         INTEGER,
                qos3MapAtoB5         INTEGER,
                qos3MapAtoB6         INTEGER,
                qos3MapAtoB7         INTEGER,
                qos3MapAtoB8         INTEGER,
                qos3MapStatus        INTEGER
            }
            
--xxx.100.11.2.9.1.1      
qos3MapType   OBJECT-TYPE
	SYNTAX      INTEGER
	            {
	               cosToIntp(0),
	               cosToDp(1),
	               expToIntp(2),
	               expToDp(3),
	               intpToCos(4),
	               intpToDscp(5),
	               intpToExp(6),
	               cosToCosGreen(7),
	               cosToCosYellow(8),
	               cosToCosRed(9),
	               cosToDscpGreen(10),
	               cosToDscpYellow(11),
	               cosToDscpRed(12)      
	            } 
        MAX-ACCESS  read-only
        STATUS      current
        DESCRIPTION 
          "the type of map,if the range of intp value beyonds 0-7,please config it in qos3MapIntpExtendTable. "
        ::= { qos3MapEntry 1 } 

--xxx.100.11.2.9.1.2       
qos3MapAtoB1   OBJECT-TYPE
	SYNTAX      INTEGER(0..119) 
        MAX-ACCESS  read-write
        STATUS      current
        DESCRIPTION "according to maptype,map a to b for the first value."
        ::= { qos3MapEntry 2 } 

--xxx.100.11.2.9.1.3      
qos3MapAtoB2   OBJECT-TYPE
	SYNTAX      INTEGER(0..119) 
        MAX-ACCESS  read-write
        STATUS      current
        DESCRIPTION "according to maptype,map a to b for the second value."
        ::= { qos3MapEntry 3 } 

--xxx.100.11.2.9.1.4      
qos3MapAtoB3   OBJECT-TYPE
	SYNTAX      INTEGER(0..119) 
        MAX-ACCESS  read-write
        STATUS      current
        DESCRIPTION "according to maptype,map a to b for the third value."
        ::= { qos3MapEntry 4 } 
        
--xxx.100.11.2.9.1.5     
qos3MapAtoB4   OBJECT-TYPE
	SYNTAX      INTEGER(0..119) 
        MAX-ACCESS  read-write
        STATUS      current
        DESCRIPTION "according to maptype,map a to b for the fourth value."
        ::= { qos3MapEntry 5 } 
        
--xxx.100.11.2.9.1.6      
qos3MapAtoB5   OBJECT-TYPE
	SYNTAX      INTEGER(0..119) 
        MAX-ACCESS  read-write
        STATUS      current
        DESCRIPTION "according to maptype,map a to b for the fifth value."
        ::= { qos3MapEntry 6 } 
        
--xxx.100.11.2.9.1.7     
qos3MapAtoB6   OBJECT-TYPE
	SYNTAX      INTEGER(0..119) 
        MAX-ACCESS  read-write
        STATUS      current
        DESCRIPTION "according to maptype,map a to b for the sixth value."
        ::= { qos3MapEntry 7 } 
        
--xxx.100.11.2.9.1.8      
qos3MapAtoB7   OBJECT-TYPE
	SYNTAX      INTEGER(0..119) 
        MAX-ACCESS  read-write
        STATUS      current
        DESCRIPTION "according to maptype,map a to b for the seventh value."
        ::= { qos3MapEntry 8 } 
        
--xxx.100.11.2.9.1.9      
qos3MapAtoB8   OBJECT-TYPE
	SYNTAX      INTEGER(0..119) 
        MAX-ACCESS  read-write
        STATUS      current
        DESCRIPTION "according to maptype,map a to b for the eighth value."
        ::= { qos3MapEntry 9 } 
        
--xxx.100.11.2.9.1.10      
qos3MapStatus   OBJECT-TYPE
	SYNTAX      INTEGER
	            {
	              createAndGo(0),
	              active(1),
	              destroy(2)
	            } 
        MAX-ACCESS  read-write
        STATUS      current
        DESCRIPTION 
         "the status of qos3MapTable"
        ::= { qos3MapEntry 10 } 
        
--********************************************************************************************************
--xxx.100.11.2.10
qos3MapDscpTable OBJECT-TYPE 
    SYNTAX  SEQUENCE OF Qos3MapDscpEntry
    MAX-ACCESS  not-accessible
    STATUS  current
    DESCRIPTION
        "this table is used for mapping between dscp and other priorities."
    ::= { qos3   10 }
            
--xxx.100.11.2.10.1
qos3MapDscpEntry OBJECT-TYPE
        SYNTAX  Qos3MapDscpEntry
        MAX-ACCESS  not-accessible
        STATUS  current
        DESCRIPTION
            "entry for mls qos dscp map configuration."
        INDEX   { qos3MapDscpType,qos3MapDscpIndex }
        ::= { qos3MapDscpTable 1 }

Qos3MapDscpEntry
        ::= SEQUENCE
            {
                qos3MapDscpType           INTEGER,
                qos3MapDscpIndex		      INTEGER,
                qos3MapDscpValue	        INTEGER,
                qos3mapDscpStatus         INTEGER
            }
            
--xxx.100.11.2.10.1.1       
qos3MapDscpType   OBJECT-TYPE
	SYNTAX      INTEGER
	            {
	              dscpToIntp(0),
	              dscpToDp(1),
	              dscpToDscp(2),
		      dscpToDscpGreen(3),
		      dscpToDscpYellow(4),
		      dscpToDscpRed(5),
		      dscpToCosGreen(6),
		      dscpToCosYellow(7),
		      dscpToCosRed(8)
	            } 
        MAX-ACCESS  read-only
        STATUS      current
        DESCRIPTION 
          "the type of map"
        ::= { qos3MapDscpEntry 1 } 

--xxx.100.11.2.10.1.2       
qos3MapDscpIndex   OBJECT-TYPE
	SYNTAX      INTEGER(0..63) 
        MAX-ACCESS  read-only
        STATUS      current
        DESCRIPTION 
         "the index of dscp"
        ::= { qos3MapDscpEntry 2 } 

--xxx.100.11.2.10.1.3      
qos3MapDscpValue   OBJECT-TYPE
	SYNTAX      INTEGER(0..63) 
        MAX-ACCESS  read-write
        STATUS      current
        DESCRIPTION 
         "the map value"
        ::= { qos3MapDscpEntry 3 } 

--xxx.100.11.2.10.1.4      
qos3mapDscpStatus   OBJECT-TYPE
	SYNTAX      INTEGER
	            {
	              createAndGo(0),
	              active(1),
	              destroy(2)
	            } 
        MAX-ACCESS  read-write
        STATUS      current
        DESCRIPTION 
          "the status of qos3MapDscpTable"
        ::= { qos3MapDscpEntry 4 } 
--********************************************************************************************************
--xxx.100.11.2.11
qos3ServicePolicyTable OBJECT-TYPE 
    SYNTAX  SEQUENCE OF Qos3ServicePolicyEntry
    MAX-ACCESS  not-accessible
    STATUS  current
    DESCRIPTION
        "bind the policy to port or vlan."
    ::= { qos3   11 }
            
--xxx.100.11.2.11.1
qos3ServicePolicyEntry OBJECT-TYPE
        SYNTAX  Qos3ServicePolicyEntry
        MAX-ACCESS  not-accessible
        STATUS  current
        DESCRIPTION
            "entry for qos bind."
        INDEX   { qos3ServicePolicyBindType,qos3ServicePolicyDirection,qos3ServicePolicyIndex }
        ::= { qos3ServicePolicyTable 1 }

Qos3ServicePolicyEntry
        ::= SEQUENCE
            {
                qos3ServicePolicyBindType           INTEGER,
                qos3ServicePolicyIndex	          INTEGER,
                qos3ServicePolicyDirection		      INTEGER,               
                qos3ServicePolicyName             DisplayString,
                qos3SercivePolicyStatus           INTEGER
            }
            
--xxx.100.11.2.11.1.1       
qos3ServicePolicyBindType   OBJECT-TYPE
	SYNTAX      INTEGER
	            {
	              port(0),
	              vlan(1)
	            
	            } 
        MAX-ACCESS  read-only
        STATUS      current
        DESCRIPTION 
         "bind the policy to port or vlan"
        ::= { qos3ServicePolicyEntry 1 } 

--xxx.100.11.2.11.1.3     
qos3ServicePolicyIndex   OBJECT-TYPE
	SYNTAX      INTEGER 
        MAX-ACCESS  read-only
        STATUS      current
        DESCRIPTION 
          "port index or vlan id"
        ::= { qos3ServicePolicyEntry 2 } 
        
--xxx.100.11.2.11.1.2      
qos3ServicePolicyDirection   OBJECT-TYPE
	SYNTAX      INTEGER
	            {
	              out(0),
	              in(1),
	              ext(2)
	            } 
        MAX-ACCESS  read-only
        STATUS      current
        DESCRIPTION 
         "the direction of binding"
        ::= { qos3ServicePolicyEntry 3 } 


--xxx.100.11.2.11.1.4     
qos3ServicePolicyName   OBJECT-TYPE
	SYNTAX      DisplayString(SIZE(1..64)) 
        MAX-ACCESS  read-write
        STATUS      current
        DESCRIPTION 
          "the policy name"
        ::= { qos3ServicePolicyEntry 4 } 

--xxx.100.11.2.11.1.5    
qos3SercivePolicyStatus   OBJECT-TYPE
	SYNTAX      INTEGER
	            {
	              createAndGo(0),
	              active(1),
	              destroy(2)
	            } 
        MAX-ACCESS  read-write
        STATUS      current
        DESCRIPTION 
          "the status of qos3ServicePolicyTable"
        ::= { qos3ServicePolicyEntry 5 } 

--********************************************************************************************************

--xxx.100.11.2.12
qos3StatisticClearTable OBJECT-TYPE 
    SYNTAX  SEQUENCE OF Qos3StatisticClearEntry
    MAX-ACCESS  not-accessible
    STATUS  current
    DESCRIPTION
        "this table is used for clearing counter statistics"
    ::= { qos3   12 }
            
--xxx.100.11.2.12
qos3StatisticClearEntry OBJECT-TYPE
        SYNTAX  Qos3StatisticClearEntry
        MAX-ACCESS  not-accessible
        STATUS  current
        DESCRIPTION
            "entry for clear statistics of vlan or port."
        INDEX   { qos3StatisticClearBindType,qos3StatisticClearDirection,qos3StatisticClearIndex }
        ::= { qos3StatisticClearTable 1 }

Qos3StatisticClearEntry
        ::= SEQUENCE
            {
                qos3StatisticClearBindType           INTEGER,
                qos3StatisticClearIndex	           INTEGER,
                qos3StatisticClearDirection		      INTEGER,
                qos3StatisticClearStatus           INTEGER
            }
            
--xxx.100.11.2.11.1       
qos3StatisticClearBindType   OBJECT-TYPE
	SYNTAX      INTEGER
	            {
	              port(0),
	              vlan(1)
	            } 
        MAX-ACCESS  read-only
        STATUS      current
        DESCRIPTION 
         "bind to port or vlan"
        ::= { qos3StatisticClearEntry 1 } 

--xxx.100.11.2.11.3     
qos3StatisticClearIndex   OBJECT-TYPE
	SYNTAX      INTEGER 
        MAX-ACCESS  read-only
        STATUS      current
        DESCRIPTION 
          "port index or vlan id"
        ::= { qos3StatisticClearEntry 2 } 
        
--xxx.100.11.2.11.2      
qos3StatisticClearDirection   OBJECT-TYPE
	SYNTAX      INTEGER
	            {
	              out(0),
	              in(1)
	            } 
        MAX-ACCESS  read-only
        STATUS      current
        DESCRIPTION 
          "the direction that you want to clear"
        ::= { qos3StatisticClearEntry 3 } 

 
--xxx.100.11.2.11.4    
qos3StatisticClearStatus   OBJECT-TYPE
	SYNTAX      INTEGER
	            {
	              disable(0),
	              enable(1)
	            } 
        MAX-ACCESS  read-write
        STATUS      current
        DESCRIPTION 
          "the status of qos3StatisticClearTable"
        ::= { qos3StatisticClearEntry 4 } 
        
        
--xxx.100.11.2.13        
qos3Ets        OBJECT IDENTIFIER ::= { qos3   13 }   
--xxx.100.11.2.13.1    
qos3EtsTable OBJECT-TYPE 
    SYNTAX  SEQUENCE OF Qos3EtsEntry
    MAX-ACCESS  not-accessible
    STATUS  current
    DESCRIPTION
        "this table is used for enabling QOS ETS and MC_UC mode."
    ::= { qos3Ets   1}

qos3EtsEntry OBJECT-TYPE
        SYNTAX  Qos3EtsEntry
        MAX-ACCESS  not-accessible
        STATUS  current
        DESCRIPTION
            "entry for enabling ETS and MC_UC."
        INDEX   { qos3EtsPortIndex}
        ::= { qos3EtsTable 1 }

Qos3EtsEntry
        ::= SEQUENCE
            {
                qos3EtsPortIndex           INTEGER,
                qos3EtsScheduleStatusConfig	  INTEGER,
                qos3EtsStatus              INTEGER
            }
                       
qos3EtsPortIndex   OBJECT-TYPE
				SYNTAX      INTEGER
        MAX-ACCESS  read-only
        STATUS      current
        DESCRIPTION 
         "port index"
        ::= { qos3EtsEntry 1 }          
        
qos3EtsScheduleStatusConfig   OBJECT-TYPE
				SYNTAX      INTEGER
							{
								normal(0),
								uc(1),
								mc(2),
								ets(3)
							}
        MAX-ACCESS  read-write
        STATUS      current
        DESCRIPTION 
         "config schedule mode."
        ::= { qos3EtsEntry 2 }   
        
qos3EtsStatus   OBJECT-TYPE
				SYNTAX      INTEGER
				{
          disable(0),
          enable(1)
				}
        MAX-ACCESS  read-write
        STATUS      current
        DESCRIPTION 
         "the status of qos3EtsTable."
        ::= { qos3EtsEntry 3 }
                
--xxx.100.11.2.13.2     
qos3McQueueBindWidthTable OBJECT-TYPE 
    SYNTAX  SEQUENCE OF Qos3McQueueBindWidthEntry
    MAX-ACCESS  not-accessible
    STATUS  current
    DESCRIPTION
        "a list of mc bindWidth configuration."
    ::= { qos3Ets   2}

qos3McQueueBindWidthEntry OBJECT-TYPE
        SYNTAX  Qos3McQueueBindWidthEntry
        MAX-ACCESS  not-accessible
        STATUS  current
        DESCRIPTION
            "entry for configuring mc bindWidth."
        INDEX   { qos3McQueueBindWidthPortIndex,qos3McQueueID}
        ::= { qos3McQueueBindWidthTable 1 }

Qos3McQueueBindWidthEntry
        ::= SEQUENCE
            {
                qos3McQueueBindWidthPortIndex           INTEGER,
                qos3McQueueID	           INTEGER,
                qos3McQueueBindWidthMin  INTEGER,
                qos3McQueueBindWidthMax  INTEGER,   
                qos3McQueueBindWidthStatus  INTEGER             
            }
                       
qos3McQueueBindWidthPortIndex   OBJECT-TYPE
				SYNTAX      INTEGER
        MAX-ACCESS  read-only
        STATUS      current
        DESCRIPTION 
         "port index"
        ::= { qos3McQueueBindWidthEntry 1 }          
        
qos3McQueueID   OBJECT-TYPE
				SYNTAX      INTEGER(1..4)
        MAX-ACCESS  read-only
        STATUS      current
        DESCRIPTION 
         "queue index."
        ::= { qos3McQueueBindWidthEntry 2 }    

qos3McQueueBindWidthMin   OBJECT-TYPE
				SYNTAX      INTEGER(0..128000)
        MAX-ACCESS  read-write
        STATUS      current
        DESCRIPTION 
         "minimize vaule of queue bindWidth"
        ::= { qos3McQueueBindWidthEntry 3 }          
                
qos3McQueueBindWidthMax   OBJECT-TYPE
				SYNTAX      INTEGER(0..128000)
        MAX-ACCESS  read-write
        STATUS      current
        DESCRIPTION 
         "maximize value of queue bindWidth."
        ::= { qos3McQueueBindWidthEntry 4 }   
        
qos3McQueueBindWidthStatus   OBJECT-TYPE
				SYNTAX      INTEGER
				{
          disable(0),
          enable(1)
				}
        MAX-ACCESS  read-write
        STATUS      current
        DESCRIPTION 
         "the status of qos3McQueueBindWidthTable."
        ::= { qos3McQueueBindWidthEntry 5 }   
        
        
--xxx.100.11.2.13.3    
qos3SchedulePolicyMapTable OBJECT-TYPE 
    SYNTAX  SEQUENCE OF Qos3SchedulePolicyMapEntry
    MAX-ACCESS  not-accessible
    STATUS  current
    DESCRIPTION
        "this table is used for building a Schedule policy and mapping the named policy to number, if you want to configure a Schedule policy,you must map at here."
    ::= { qos3Ets   3}

qos3SchedulePolicyMapEntry OBJECT-TYPE
        SYNTAX  Qos3SchedulePolicyMapEntry
        MAX-ACCESS  not-accessible
        STATUS  current
        DESCRIPTION
            "entry for building schedule policy."
        INDEX   { qos3SchedulePolicyMapIndex}
        ::= { qos3SchedulePolicyMapTable 1 }

Qos3SchedulePolicyMapEntry
        ::= SEQUENCE
            {
                qos3SchedulePolicyMapIndex           INTEGER,
                qos3SchedulePolicyName           DisplayString,
                qos3SchedulePolicyStatus         INTEGER       
            }
                       
qos3SchedulePolicyMapIndex   OBJECT-TYPE
				SYNTAX      INTEGER
        MAX-ACCESS  read-only
        STATUS      current
        DESCRIPTION 
         "the range is 0-(2^64 - 1)."
        ::= { qos3SchedulePolicyMapEntry 1 }          
        
qos3SchedulePolicyName   OBJECT-TYPE
				SYNTAX      DisplayString(SIZE(1..64))
        MAX-ACCESS  read-write
        STATUS      current
        DESCRIPTION 
         "the schedule policy name."
        ::= { qos3SchedulePolicyMapEntry 2 }           
        
qos3SchedulePolicyStatus   OBJECT-TYPE
				SYNTAX      INTEGER
				{
          createAndGo(0),
          active(1),
          destroy(2)
				}
	      MAX-ACCESS  read-write
	      STATUS      current
	      DESCRIPTION 
	       "the status of qos3SchedulePolicyGroupTable."
	      ::= { qos3SchedulePolicyMapEntry 3 }  


qos3NodeScheduleTable OBJECT-TYPE 
    SYNTAX  SEQUENCE OF Qos3NodeScheduleEntry
    MAX-ACCESS  not-accessible
    STATUS  current
    DESCRIPTION
        "this table is used for building a Schedule node."
    ::= { qos3Ets   4}

qos3NodeScheduleEntry OBJECT-TYPE
        SYNTAX  Qos3NodeScheduleEntry
        MAX-ACCESS  not-accessible
        STATUS  current
        DESCRIPTION
            "entry for building schedule policy."
        INDEX   { qos3NodeSchedulePolicyIndex,qos3NodeScheduleLevelID,qos3NodeScheduleNodeID}
        ::= { qos3NodeScheduleTable 1 }

Qos3NodeScheduleEntry
        ::= SEQUENCE
            {
                qos3NodeSchedulePolicyIndex           INTEGER,
                qos3NodeScheduleLevelID               INTEGER,
                qos3NodeScheduleNodeID                INTEGER,
                qos3NodeScheduleStatus                INTEGER       
            }
                       
qos3NodeSchedulePolicyIndex   OBJECT-TYPE
				SYNTAX      INTEGER
        MAX-ACCESS  read-only
        STATUS      current
        DESCRIPTION 
         "policy index."
        ::= { qos3NodeScheduleEntry 1 }          
        
qos3NodeScheduleLevelID   OBJECT-TYPE
				SYNTAX      INTEGER(1..3)
        MAX-ACCESS  read-only
        STATUS      current
        DESCRIPTION 
         "level ID."
        ::= { qos3NodeScheduleEntry 2 }   
        
qos3NodeScheduleNodeID   OBJECT-TYPE
				SYNTAX      INTEGER(1..4)
        MAX-ACCESS  read-only
        STATUS      current
        DESCRIPTION 
         "node ID. range of it's value is determined by level ID,for level 1,it can only be 1;
         for level 2 and level 3,the range is 1-4."
        ::= { qos3NodeScheduleEntry 3 }         
        
qos3NodeScheduleStatus   OBJECT-TYPE
				SYNTAX      INTEGER
				{
          createAndGo(0),
          active(1),
          destroy(2)
				}
	      MAX-ACCESS  read-write
	      STATUS      current
	      DESCRIPTION 
	       "the status of qos3NodeScheduleTable."
	      ::= { qos3NodeScheduleEntry 4 }  
	            
--xxx.100.11.2.13.4  	      
qos3ScheduleQueueAlgorithmTable OBJECT-TYPE 
    SYNTAX  SEQUENCE OF Qos3ScheduleQueueAlgorithmEntry
    MAX-ACCESS  not-accessible
    STATUS  current
    DESCRIPTION
        "this table is used for schedule queue algorithm configuration."
    ::= { qos3Ets   5}

qos3ScheduleQueueAlgorithmEntry OBJECT-TYPE
        SYNTAX  Qos3ScheduleQueueAlgorithmEntry
        MAX-ACCESS  not-accessible
        STATUS  current
        DESCRIPTION
            "entry for configuring schedule queue algorithm."
        INDEX   { qos3ScheduleQueueAlgorithmPolicyIndex,qos3ScheduleQueueAlgorithmLevelID,qos3ScheduleQueueAlgorithmNodeID}
        ::= { qos3ScheduleQueueAlgorithmTable 1 }

Qos3ScheduleQueueAlgorithmEntry
        ::= SEQUENCE
            {
                qos3ScheduleQueueAlgorithmPolicyIndex       INTEGER,
                qos3ScheduleQueueAlgorithmLevelID           INTEGER,
                qos3ScheduleQueueAlgorithmNodeID            INTEGER, 
                qos3ScheduleQueueAlgorithmConfig      			INTEGER,
                qos3ScheduleQueueAlgorithmStatus      			INTEGER                
            }
                       
qos3ScheduleQueueAlgorithmPolicyIndex   OBJECT-TYPE
				SYNTAX      INTEGER
        MAX-ACCESS  read-only
        STATUS      current
        DESCRIPTION 
         "schedule policy map Index."
        ::= { qos3ScheduleQueueAlgorithmEntry 1 }          
        
qos3ScheduleQueueAlgorithmLevelID   OBJECT-TYPE
				SYNTAX      INTEGER(1..3)
        MAX-ACCESS  read-only
        STATUS      current
        DESCRIPTION 
         "level ID."
        ::= { qos3ScheduleQueueAlgorithmEntry 2 }           
 
 
qos3ScheduleQueueAlgorithmNodeID   OBJECT-TYPE
				SYNTAX      INTEGER(1..4)
        MAX-ACCESS  read-only
        STATUS      current
        DESCRIPTION 
         "node ID. range of it's value is determined by level ID,for level 1,it can only be 1;
         for level 2 and level 3,the range is 1-4."
        ::= { qos3ScheduleQueueAlgorithmEntry 3 }          
        
qos3ScheduleQueueAlgorithmConfig   OBJECT-TYPE
				SYNTAX      INTEGER
				{
					rr(0),
					sp(1),
					wrr(2),
					wdrr(3)
				}
        MAX-ACCESS  read-write
        STATUS      current
        DESCRIPTION 
         "schedule queue algorithm."
        ::= { qos3ScheduleQueueAlgorithmEntry 4 }    
           
qos3ScheduleQueueAlgorithmStatus   OBJECT-TYPE
				SYNTAX      INTEGER
				{
          createAndGo(0),
          active(1),
          destroy(2)
				}
	      MAX-ACCESS  read-write
	      STATUS      current
	      DESCRIPTION 
	       "the status of qos3ScheduleQueueAlgorithmTable."
	      ::= { qos3ScheduleQueueAlgorithmEntry 5 }        
	      
--xxx.100.11.2.13.5  	      
qos3ScheduleQueueWeightTable OBJECT-TYPE 
    SYNTAX  SEQUENCE OF Qos3ScheduleQueueWeightEntry
    MAX-ACCESS  not-accessible
    STATUS  current
    DESCRIPTION
        "this table is used for schedule queue weight configuration."
    ::= { qos3Ets   6}

qos3ScheduleQueueWeightEntry OBJECT-TYPE
        SYNTAX  Qos3ScheduleQueueWeightEntry
        MAX-ACCESS  not-accessible
        STATUS  current
        DESCRIPTION
            "entry for configuring schedule queue weight."
        INDEX   { qos3ScheduleQueueWeightPolicyIndex,qos3ScheduleQueueWeightLevelID,qos3ScheduleQueueWeightNodeID,qos3ScheduleQueueAlgorithm,qos3ScheduleQueueWeightQueueID}
        ::= { qos3ScheduleQueueWeightTable 1 }

Qos3ScheduleQueueWeightEntry
        ::= SEQUENCE
            {
                qos3ScheduleQueueWeightPolicyIndex       INTEGER,
                qos3ScheduleQueueWeightLevelID           INTEGER,
                qos3ScheduleQueueWeightNodeID            INTEGER, 
                qos3ScheduleQueueAlgorithm               INTEGER,
                qos3ScheduleQueueWeightQueueID           INTEGER,
                qos3ScheduleQueueWeightValue      			INTEGER,
                qos3ScheduleQueueWeightStatus            INTEGER
            }
                       
qos3ScheduleQueueWeightPolicyIndex   OBJECT-TYPE
				SYNTAX      INTEGER
        MAX-ACCESS  read-only
        STATUS      current
        DESCRIPTION 
         "schedule policy map Index."
        ::= { qos3ScheduleQueueWeightEntry 1 }          
        
qos3ScheduleQueueWeightLevelID   OBJECT-TYPE
				SYNTAX      INTEGER
        MAX-ACCESS  read-only
        STATUS      current
        DESCRIPTION 
         "level ID."
        ::= { qos3ScheduleQueueWeightEntry 2 }  
                 
qos3ScheduleQueueWeightNodeID   OBJECT-TYPE
				SYNTAX      INTEGER
        MAX-ACCESS  read-only
        STATUS      current
        DESCRIPTION 
         "node ID. range of it's value is determined by level ID,for level 1,it can only be 1;
         for level 2 and level 3,the range is 1-4."
        ::= { qos3ScheduleQueueWeightEntry 3 } 
        
qos3ScheduleQueueAlgorithm   OBJECT-TYPE
				SYNTAX      INTEGER
				{
					wrr(0),
					wdrr(1)
				}
        MAX-ACCESS  read-only
        STATUS      current
        DESCRIPTION 
         "queue algorithm."
        ::= { qos3ScheduleQueueWeightEntry 4 }    
         
qos3ScheduleQueueWeightQueueID   OBJECT-TYPE
				SYNTAX      INTEGER(0..18)
        MAX-ACCESS  read-only
        STATUS      current
        DESCRIPTION 
         "queue ID."
        ::= { qos3ScheduleQueueWeightEntry 5 }    
                     
qos3ScheduleQueueWeightValue   OBJECT-TYPE
				SYNTAX      INTEGER(0..32767) 
        MAX-ACCESS  read-write
        STATUS      current
        DESCRIPTION 
         "queue weight value."
        ::= { qos3ScheduleQueueWeightEntry 6 }       
          
qos3ScheduleQueueWeightStatus   OBJECT-TYPE
				SYNTAX      INTEGER
				{
          disable(0),
          enable(1)
				}
	      MAX-ACCESS  read-write
	      STATUS      current
	      DESCRIPTION 
	       "the status of qos3ScheduleQueueWeightTable."
	      ::= { qos3ScheduleQueueWeightEntry 7 }  
	      
--xxx.100.11.2.13.6  	      
qos3ScheduleQueueInputTable OBJECT-TYPE 
    SYNTAX  SEQUENCE OF Qos3ScheduleQueueInputEntry
    MAX-ACCESS  not-accessible
    STATUS  current
    DESCRIPTION
        "this table is used for schedule queue input configuration."
    ::= { qos3Ets   7}

qos3ScheduleQueueInputEntry OBJECT-TYPE
        SYNTAX  Qos3ScheduleQueueInputEntry
        MAX-ACCESS  not-accessible
        STATUS  current
        DESCRIPTION
            "entry for configuring schedule queue input."
        INDEX   { qos3ScheduleQueueInputPolicyIndex,qos3ScheduleQueueInputLevelID,qos3ScheduleQueueInputNodeID,qos3ScheduleQueueInputQueueID}
        ::= { qos3ScheduleQueueInputTable 1 }

Qos3ScheduleQueueInputEntry
        ::= SEQUENCE
            {
                qos3ScheduleQueueInputPolicyIndex       INTEGER,
                qos3ScheduleQueueInputLevelID           INTEGER,
                qos3ScheduleQueueInputNodeID            INTEGER, 
                qos3ScheduleQueueInputQueueID           INTEGER,
                qos3ScheduleQueueInputType      			  INTEGER,
                qos3ScheduleQueueInputTypeValue         INTEGER,
                qos3ScheduleQueueInputStatus            INTEGER
            }
                       
qos3ScheduleQueueInputPolicyIndex   OBJECT-TYPE
				SYNTAX      INTEGER
        MAX-ACCESS  read-only
        STATUS      current
        DESCRIPTION 
         "schedule policy map Index."
        ::= { qos3ScheduleQueueInputEntry 1 }          
        
qos3ScheduleQueueInputLevelID   OBJECT-TYPE
				SYNTAX      INTEGER
        MAX-ACCESS  read-only
        STATUS      current
        DESCRIPTION 
         "level ID."
        ::= { qos3ScheduleQueueInputEntry 2 }           
 
 
qos3ScheduleQueueInputNodeID   OBJECT-TYPE
				SYNTAX      INTEGER
        MAX-ACCESS  read-only
        STATUS      current
        DESCRIPTION 
         "node ID. range of it's value is determined by level ID,for level 1,it can only be 1;
         for level 2 and level 3,the range is 1-4."
        ::= { qos3ScheduleQueueInputEntry 3 }          
        
qos3ScheduleQueueInputQueueID   OBJECT-TYPE
				SYNTAX      INTEGER
        MAX-ACCESS  read-only
        STATUS      current
        DESCRIPTION 
         "queue ID."
        ::= { qos3ScheduleQueueInputEntry 4 }  
             
qos3ScheduleQueueInputType   OBJECT-TYPE
				SYNTAX      INTEGER
				{
					uc(0),
					mc(1),
					node(2)
				}
        MAX-ACCESS  read-write
        STATUS      current
        DESCRIPTION 
         "input type of queue."
        ::= { qos3ScheduleQueueInputEntry 5 }   
        
qos3ScheduleQueueInputTypeValue   OBJECT-TYPE
				SYNTAX      INTEGER
        MAX-ACCESS  read-write
        STATUS      current
        DESCRIPTION 
         "value of the input type,the value range for uc is 1-18,the value range for mc is 1-4,the value range for node is 1-4."
        ::= { qos3ScheduleQueueInputEntry 6 }
                 
qos3ScheduleQueueInputStatus   OBJECT-TYPE
				SYNTAX      INTEGER
				{
          disable(0),
          enable(1)
				}
	      MAX-ACCESS  read-write
	      STATUS      current
	      DESCRIPTION 
	       "the status of qos3ScheduleBindWidthTable."
	      ::= { qos3ScheduleQueueInputEntry 7 } 
	      	 
--xxx.100.11.2.13.7  
qos3ScheduleBindWidthTable OBJECT-TYPE 
    SYNTAX  SEQUENCE OF Qos3ScheduleBindWidthEntry
    MAX-ACCESS  not-accessible
    STATUS  current
    DESCRIPTION
        "this table is used for schedule bindWidth configuration."
    ::= { qos3Ets   8}

qos3ScheduleBindWidthEntry OBJECT-TYPE
        SYNTAX  Qos3ScheduleBindWidthEntry
        MAX-ACCESS  not-accessible
        STATUS  current
        DESCRIPTION
            "entry for configuring schedule bindWidth."
        INDEX   { qos3ScheduleBindWidthPolicyIndex,qos3ScheduleBindWidthLevelID,qos3ScheduleBindWidthNodeID}
        ::= { qos3ScheduleBindWidthTable 1 }

Qos3ScheduleBindWidthEntry
        ::= SEQUENCE
            {
                qos3ScheduleBindWidthPolicyIndex       INTEGER,
                qos3ScheduleBindWidthLevelID           INTEGER,
                qos3ScheduleBindWidthNodeID            INTEGER, 
                qos3ScheduleBindWidthMin      			   INTEGER,
                qos3ScheduleBindWidthMax               INTEGER,
                qos3ScheduleBindWidthStatus            INTEGER
            }
                       
qos3ScheduleBindWidthPolicyIndex   OBJECT-TYPE
				SYNTAX      INTEGER
        MAX-ACCESS  read-only
        STATUS      current
        DESCRIPTION 
         "schedule policy map Index."
        ::= { qos3ScheduleBindWidthEntry 1 }          
        
qos3ScheduleBindWidthLevelID   OBJECT-TYPE
				SYNTAX      INTEGER
        MAX-ACCESS  read-only
        STATUS      current
        DESCRIPTION 
         "level ID."
        ::= { qos3ScheduleBindWidthEntry 2 }           
 
 
qos3ScheduleBindWidthNodeID   OBJECT-TYPE
				SYNTAX      INTEGER
        MAX-ACCESS  read-only
        STATUS      current
        DESCRIPTION 
         "node ID. range of it's value is determined by level ID,for level 1,it can only be 1;
         for level 2 and level 3,the range is 1-4."
        ::= { qos3ScheduleBindWidthEntry 3 }          
        
qos3ScheduleBindWidthMin   OBJECT-TYPE
				SYNTAX      INTEGER(0..12800)
        MAX-ACCESS  read-write
        STATUS      current
        DESCRIPTION 
         "minimize value of schedule bindWidth."
        ::= { qos3ScheduleBindWidthEntry 4 }  
             
qos3ScheduleBindWidthMax   OBJECT-TYPE
				SYNTAX      INTEGER(0..12800)
        MAX-ACCESS  read-write
        STATUS      current
        DESCRIPTION 
         "maximize value of schedule bindWidth."
        ::= { qos3ScheduleBindWidthEntry 5 }   
                 
qos3ScheduleBindWidthStatus   OBJECT-TYPE
				SYNTAX      INTEGER
				{
          disable(0),
          enable(1)
				}
	      MAX-ACCESS  read-write
	      STATUS      current
	      DESCRIPTION 
	       "the status of qos3ScheduleBindWidthTable."
	      ::= { qos3ScheduleBindWidthEntry 6 } 	
	      
--xxx.100.11.2.13.8  	      
qos3SchedulePolicyBindTable OBJECT-TYPE 
    SYNTAX  SEQUENCE OF Qos3SchedulePolicyBindEntry
    MAX-ACCESS  not-accessible
    STATUS  current
    DESCRIPTION
        "this table is used for binding schedule policy to port."
    ::= { qos3Ets   9}

qos3SchedulePolicyBindEntry OBJECT-TYPE
        SYNTAX  Qos3SchedulePolicyBindEntry
        MAX-ACCESS  not-accessible
        STATUS  current
        DESCRIPTION
            "entry for binding schedule policy."
        INDEX   { qos3SchedulePolicyBindPortIndex}
        ::= { qos3SchedulePolicyBindTable 1 }

Qos3SchedulePolicyBindEntry
        ::= SEQUENCE
            {
                qos3SchedulePolicyBindPortIndex        INTEGER,
                qos3SchedulePolicyBindPolicyName       DisplayString,
                qos3SchedulePolicyBindStatus           INTEGER       
            }
                       
qos3SchedulePolicyBindPortIndex   OBJECT-TYPE
				SYNTAX      INTEGER
        MAX-ACCESS  read-only
        STATUS      current
        DESCRIPTION 
         "port Index."
        ::= { qos3SchedulePolicyBindEntry 1 }          
        
qos3SchedulePolicyBindPolicyName   OBJECT-TYPE
				SYNTAX      DisplayString(SIZE(1..64))
        MAX-ACCESS  read-write
        STATUS      current
        DESCRIPTION 
         "the schedule policy name."
        ::= { qos3SchedulePolicyBindEntry 2 }           
        
qos3SchedulePolicyBindStatus   OBJECT-TYPE
				SYNTAX      INTEGER
				{
          disable(0),
          enable(1)
				}
	      MAX-ACCESS  read-write
	      STATUS      current
	      DESCRIPTION 
	       "the status of qos3SchedulePolicyBindTable."
	      ::= { qos3SchedulePolicyBindEntry 3 } 
	      
--xxx.100.11.2.14  	      
qos3MapIntpExtendTable 	 OBJECT-TYPE 
    SYNTAX  SEQUENCE OF Qos3MapIntpExtendEntry
    MAX-ACCESS  not-accessible
    STATUS  current
    DESCRIPTION
        "this table is used for mapping between intp and other priorities,the range of value for intp is 0-119."
    ::= { qos3   14}      
--xxx.100.11.2.10.1
qos3MapIntpExtendEntry OBJECT-TYPE
        SYNTAX  Qos3MapIntpExtendEntry
        MAX-ACCESS  not-accessible
        STATUS  current
        DESCRIPTION
            "entry for mls qos intp map configuration."
        INDEX   { qos3MapIntpExtendType,qos3MapIntpExtendIndex }
        ::= { qos3MapIntpExtendTable 1 }

Qos3MapIntpExtendEntry
        ::= SEQUENCE
            {
                qos3MapIntpExtendType           INTEGER,
                qos3MapIntpExtendIndex		      INTEGER,
                qos3MapIntpExtendValue	        INTEGER,
                qos3mapIntpExtendStatus         INTEGER
            }
            
--xxx.100.11.2.10.1.1       
qos3MapIntpExtendType   OBJECT-TYPE
	SYNTAX      INTEGER
	            {
			intpToCos(0),
			intpToDscp(1),
			intpToExp(2),	 
			intpToQueue(3),
			intpToDp(4),
			intpToIntpRed(5),
			intpToIntpYellow(6)          
	            } 
        MAX-ACCESS  read-only
        STATUS      current
        DESCRIPTION 
          "the type of map"
        ::= { qos3MapIntpExtendEntry 1 } 

--xxx.100.11.2.10.1.2       
qos3MapIntpExtendIndex   OBJECT-TYPE
	SYNTAX      INTEGER(0..119) 
        MAX-ACCESS  read-only
        STATUS      current
        DESCRIPTION 
         "the index of intp"
        ::= { qos3MapIntpExtendEntry 2 } 

--xxx.100.11.2.10.1.3      
qos3MapIntpExtendValue   OBJECT-TYPE
	SYNTAX      INTEGER(0..119) 
        MAX-ACCESS  read-write
        STATUS      current
        DESCRIPTION 
         "the map value"
        ::= { qos3MapIntpExtendEntry 3 } 

--xxx.100.11.2.10.1.4      
qos3mapIntpExtendStatus   OBJECT-TYPE
	SYNTAX      INTEGER
	            {
	              createAndGo(0),
	              active(1),
	              destroy(2)
	            } 
        MAX-ACCESS  read-write
        STATUS      current
        DESCRIPTION 
          "the status of qos3MapIntpExtendTable"
        ::= { qos3MapIntpExtendEntry 4 } 	     
         
--xxx.100.11.2.15       
qos3EgressRemark        OBJECT IDENTIFIER ::= { qos3   15 }   	
--xxx.100.11.2.15.1        
qos3EgressGreenRemark   OBJECT-TYPE
			SYNTAX      INTEGER
			{
        disable(0),
        enable(1)
			}
      MAX-ACCESS  read-write
      STATUS      current
      DESCRIPTION 
       "enabling egress remark on green packet."
      ::= { qos3EgressRemark 1 }  
                                                                                                                                                                                                                                                                                                                                                                                                                                                                                                                                                                                                                                     
--xxx.100.11.2.16        
showQos3    OBJECT IDENTIFIER ::= { qos3   16}          
    
--xxx.100.11.2.16.1
showQos3VlanTable OBJECT-TYPE                --add 2015/12/1
    SYNTAX  SEQUENCE OF ShowQos3VlanEntry
    MAX-ACCESS  not-accessible
    STATUS  current
    DESCRIPTION
        " Show Qos3 Vlan Table"
    ::= { showQos3   1}
            
--xxx.100.11.2.16.1.1
showQos3VlanEntry OBJECT-TYPE
        SYNTAX  ShowQos3VlanEntry
        MAX-ACCESS  not-accessible
        STATUS  current
        DESCRIPTION
            "index is vlan id"
        INDEX   { showQos3VlanId, showQos3PolicyDirection, showQos3ClassmapName}
        ::= { showQos3VlanTable 1 }

ShowQos3VlanEntry
        ::= SEQUENCE
            {
                showQos3VlanId                INTEGER,
                showQos3PolicyDirection       INTEGER,
                showQos3ClassmapName          DisplayString,
                showQos3VlanInCounter	      Counter64,
                showQos3VlanOutCounter        Counter64,
                showQos3VlanGreenCounter	  Counter64,
                showQos3VlanYellowCounter     Counter64,
                showQos3VlanRedCounter	      Counter64
             }
            
--xxx.100.11.2.16.1.1.1
showQos3VlanId  OBJECT-TYPE
            SYNTAX  INTEGER (1..4094)
            MAX-ACCESS  not-accessible
            STATUS  current
            DESCRIPTION
                " show qos vlan id."
            ::= { showQos3VlanEntry 1 }
            
--xxx.100.11.2.16.1.1.2
showQos3PolicyDirection OBJECT-TYPE
            SYNTAX  INTEGER
            	    {
               		in(0),
               		out(1), 
               		pre(2),
               		ext(3)
            	    }
            MAX-ACCESS  not-accessible
            STATUS  current
            DESCRIPTION
                "QoS Policy direction"
            ::= { showQos3VlanEntry 2 }

--xxx.100.11.2.16.1.1.3
showQos3ClassmapName OBJECT-TYPE
            SYNTAX  DisplayString (SIZE(1..64))
            MAX-ACCESS  not-accessible
            STATUS  current
            DESCRIPTION
                "QoS class map name"
            ::= { showQos3VlanEntry 3 }
            
--xxx.100.11.2.16.1.1.4         
showQos3VlanInCounter  OBJECT-TYPE
	      SYNTAX      Counter64
        MAX-ACCESS  read-only
        STATUS      current
        DESCRIPTION "in vlan counter"
        ::= { showQos3VlanEntry 4 }   
        
--xxx.100.11.2.16.1.1.5         
showQos3VlanOutCounter  OBJECT-TYPE
	      SYNTAX      Counter64
        MAX-ACCESS  read-only
        STATUS      current
        DESCRIPTION "out vlan counter"
        ::= { showQos3VlanEntry 5 }       
        
--xxx.100.11.2.16.1.1.6         
showQos3VlanGreenCounter  OBJECT-TYPE
	      SYNTAX      Counter64
        MAX-ACCESS  read-only
        STATUS      current
        DESCRIPTION "green vlan counter"
        ::= { showQos3VlanEntry 6 }   
        
--xxx.100.11.2.16.1.1.7        
showQos3VlanYellowCounter  OBJECT-TYPE
	      SYNTAX      Counter64
        MAX-ACCESS  read-only
        STATUS      current
        DESCRIPTION "yellow vlan counter"
        ::= { showQos3VlanEntry 7 } 
         
--xxx.100.11.2.16.1.1.8        
showQos3VlanRedCounter  OBJECT-TYPE
	      SYNTAX      Counter64
        MAX-ACCESS  read-only
        STATUS      current
        DESCRIPTION "red vlan counter"
        ::= { showQos3VlanEntry 8 }   



--xxx.100.11.2.17
showQos3QueueStatisticsTable OBJECT-TYPE                --add 2017/10/18
    SYNTAX  SEQUENCE OF ShowQos3QueueStatisticsEntry
    MAX-ACCESS  not-accessible
    STATUS  current
    DESCRIPTION
        " Show Qos3 Queue Statistics Table"
    ::= { qos3   17}
            
--xxx.100.11.2.17.1
showQos3QueueStatisticsEntry OBJECT-TYPE
        SYNTAX  ShowQos3QueueStatisticsEntry
        MAX-ACCESS  not-accessible
        STATUS  current
        DESCRIPTION
            "index is port id"
        INDEX   { showQos3QueueStatisticsPortIndex}
        ::= { showQos3QueueStatisticsTable 1 }

ShowQos3QueueStatisticsEntry
        ::= SEQUENCE
            {
                showQos3QueueStatisticsPortIndex                INTEGER,
                showQos3QueueStatisticsQueueID                  INTEGER,
                showQos3QueueStatisticsPassedPacket             INTEGER,
                showQos3QueueStatisticsDropedPacket	            INTEGER

             }
            
--xxx.100.11.2.17.1.1
showQos3QueueStatisticsPortIndex  OBJECT-TYPE
            SYNTAX  INTEGER
            MAX-ACCESS  read-only
            STATUS  current
            DESCRIPTION
                " show qos port id."
            ::= { showQos3QueueStatisticsEntry 1 }
            
--xxx.100.11.2.17.1.2
showQos3QueueStatisticsQueueID OBJECT-TYPE
            SYNTAX  INTEGER
            MAX-ACCESS  read-only
            STATUS  current
            DESCRIPTION
                "show qos queue id"
            ::= { showQos3QueueStatisticsEntry 2 }

--xxx.100.11.2.17.1.3
showQos3QueueStatisticsPassedPacket OBJECT-TYPE
            SYNTAX  INTEGER
            MAX-ACCESS  read-only
            STATUS  current
            DESCRIPTION
                "QoS queue statististics passed packet"
            ::= { showQos3QueueStatisticsEntry 3 }
            
--xxx.100.11.2.17.1.4       
showQos3QueueStatisticsDropedPacket  OBJECT-TYPE
	      SYNTAX      INTEGER
        MAX-ACCESS  read-only
        STATUS      current
        DESCRIPTION "QoS queue statististics drop packet"
        ::= { showQos3QueueStatisticsEntry 4 }   
     
--xxx.100.11.2.18
showQos3MCQueueStatisticsTable OBJECT-TYPE                --add 2018/1/16
    SYNTAX  SEQUENCE OF ShowQos3MCQueueStatisticsEntry
    MAX-ACCESS  not-accessible
    STATUS  current
    DESCRIPTION
        " Show Qos3 MC-Queue Statistics Table"
    ::= { qos3   18}
                
--xxx.100.11.2.18.1
showQos3MCQueueStatisticsEntry OBJECT-TYPE
        SYNTAX  ShowQos3MCQueueStatisticsEntry
        MAX-ACCESS  not-accessible
        STATUS  current
        DESCRIPTION
            "index is port id for MC-QUEUE"
        INDEX   { showQos3MCQueueStatisticsPortIndex}
        ::= { showQos3MCQueueStatisticsTable 1 }

ShowQos3MCQueueStatisticsEntry
        ::= SEQUENCE
            {
                showQos3MCQueueStatisticsPortIndex                INTEGER,
                showQos3MCQueueStatisticsQueueID                  INTEGER,
                showQos3MCQueueStatisticsPassedPacket             INTEGER,
                showQos3MCQueueStatisticsDropedPacket	            INTEGER

             }
            
--xxx.100.11.2.18.1.1
showQos3MCQueueStatisticsPortIndex  OBJECT-TYPE
            SYNTAX  INTEGER
            MAX-ACCESS  read-only
            STATUS  current
            DESCRIPTION
                " show qos port id for MC-QUEUE."
            ::= { showQos3MCQueueStatisticsEntry 1 }
            
--xxx.100.11.2.18.1.2
showQos3MCQueueStatisticsQueueID OBJECT-TYPE
            SYNTAX  INTEGER
            MAX-ACCESS  read-only
            STATUS  current
            DESCRIPTION
                "show qos MC-queue id"
            ::= { showQos3MCQueueStatisticsEntry 2 }

--xxx.100.11.2.18.1.3
showQos3MCQueueStatisticsPassedPacket OBJECT-TYPE
            SYNTAX  INTEGER
            MAX-ACCESS  read-only
            STATUS  current
            DESCRIPTION
                "QoS MC-queue statististics passed packet"
            ::= { showQos3MCQueueStatisticsEntry 3 }
            
--xxx.100.11.2.18.1.4       
showQos3MCQueueStatisticsDropedPacket  OBJECT-TYPE
	      SYNTAX      INTEGER
        MAX-ACCESS  read-only
        STATUS      current
        DESCRIPTION "QoS MC-queue statististics drop packet"
        ::= { showQos3MCQueueStatisticsEntry 4 }         
                                                                                                                                                                                                                                                                                                                                                                                                                                                                                                                                                                                                                        
--********************************************************************************************************
--********************************************************************************************************
--xxx.100.12.3
mirrorSrcCpuTable OBJECT-TYPE 
    SYNTAX  SEQUENCE OF MirrorSrcCpuEntry
    MAX-ACCESS  not-accessible
    STATUS  current
    DESCRIPTION
        "Src Cpu for mirrored packets."
    ::= { primirror   3}
            
--xxx.100.12.3.1
mirrorSrcCpuEntry OBJECT-TYPE
        SYNTAX  MirrorSrcCpuEntry
        MAX-ACCESS  not-accessible
        STATUS  current
        DESCRIPTION
            "Src Cpu for mirrored packets."
        INDEX   { mirrorSrcCpuSession , mirrorSrcCpuDirect , mirrorSrcCpuSlot }
        ::= { mirrorSrcCpuTable 1 }

MirrorSrcCpuEntry
        ::= SEQUENCE
            {
                mirrorSrcCpuSession    INTEGER,
                mirrorSrcCpuDirect     INTEGER,
                mirrorSrcCpuSlot       INTEGER,
                mirrorSrcCpuStatus     INTEGER     
            }
            
--xxx.100.12.3.1.1       
mirrorSrcCpuSession   OBJECT-TYPE
	SYNTAX      INTEGER(4)	
        MAX-ACCESS  read-only
        STATUS      current
        DESCRIPTION "Session ID."
        ::= { mirrorSrcCpuEntry 1 } 
          
--xxx.100.12.3.1.2       
mirrorSrcCpuDirect   OBJECT-TYPE
	SYNTAX      INTEGER 
		{
               		rx(1),
               		tx(2)		
		}	
        MAX-ACCESS  read-only
        STATUS      current
        DESCRIPTION "Direction of  mirror."
        ::= { mirrorSrcCpuEntry 2 }   
        
--xxx.100.12.3.1.3       
mirrorSrcCpuSlot   OBJECT-TYPE
	SYNTAX      INTEGER	
        MAX-ACCESS  read-only
        STATUS      current
        DESCRIPTION "Src cpu slot index."
        ::= { mirrorSrcCpuEntry 3 } 
        
--xxx.100.12.3.1.4       
mirrorSrcCpuStatus   OBJECT-TYPE
	SYNTAX      INTEGER
		    {
            	    
               		active(1),
               		destroy(2)		    	
		    }	
        MAX-ACCESS  read-create
        STATUS      current
        DESCRIPTION "Status."
        ::= { mirrorSrcCpuEntry 4 }         
 
--******************************************************************************************************** 
 
--xxx.100.12.4
mirrorReflectorPortTable OBJECT-TYPE 
    SYNTAX  SEQUENCE OF MirrorReflectorPortEntry
    MAX-ACCESS  not-accessible
    STATUS  current
    DESCRIPTION
        "mirror reflector destination port configuration Table of Rspan.
        The information about the reflector destination port and 
        its associated session will be specified by this table,which 
        will not present itself in the mirrorDestTable. Which means 
        the mirrorReflectorPortTable and the mirrorDestTable is 
        independent from each other."
    ::= { primirror   4}
 
--xxx.100.12.4.1
mirrorReflectorPortEntry OBJECT-TYPE
        SYNTAX  MirrorReflectorPortEntry
        MAX-ACCESS  not-accessible
        STATUS  current
        DESCRIPTION
            "mirror destination port configuration of Rspan."
        INDEX   { mirrorReflectorPortSession , mirrorReflectorPort }
        ::= { mirrorReflectorPortTable 1 }

MirrorReflectorPortEntry
        ::= SEQUENCE
            {
                mirrorReflectorPortSession           INTEGER,
                mirrorReflectorPort                  INTEGER,          
                mirrorReflectorPortStatus            INTEGER
            }                
        
        
--xxx.100.12.4.1.1       
mirrorReflectorPortSession   OBJECT-TYPE
	SYNTAX      INTEGER (1..4)	
        MAX-ACCESS  read-only
        STATUS      current
        DESCRIPTION "Session ID."
        ::= { mirrorReflectorPortEntry 1 }         

--xxx.100.12.4.1.2       
mirrorReflectorPort   OBJECT-TYPE
	SYNTAX      INTEGER		
        MAX-ACCESS  read-only
        STATUS      current
        DESCRIPTION "mirror reflector destination port number."
        ::= { mirrorReflectorPortEntry 2 }  
 
         
--xxx.100.12.4.1.3       
mirrorReflectorPortStatus   OBJECT-TYPE
	SYNTAX      INTEGER
		    {
            	    
               		active(1),
               		destroy(2)		    	
		    }	
        MAX-ACCESS  read-create
        STATUS      current
        DESCRIPTION "The configuration status of the reflector destination port and its associated session."
        ::= { mirrorReflectorPortEntry 3 }  
                   
--********************************************************************************************************

--xxx.100.12.5
mirrorRspanVlanTable OBJECT-TYPE 
    SYNTAX  SEQUENCE OF MirrorRspanVlanEntry
    MAX-ACCESS  not-accessible
    STATUS  current
    DESCRIPTION
        "Vlan configuration Table of Rspan."
    ::= { primirror   5}
 
--xxx.100.12.5.1
mirrorRspanVlanEntry OBJECT-TYPE
        SYNTAX  MirrorRspanVlanEntry
        MAX-ACCESS  not-accessible
        STATUS  current
        DESCRIPTION
            "Vlan configuration of Rspan."
        INDEX   { mirrorRspanVlan }
        ::= { mirrorRspanVlanTable 1 }

MirrorRspanVlanEntry
        ::= SEQUENCE
            {
                mirrorRspanVlan                INTEGER,
                mirrorRspanVlanStatus          INTEGER
            }
            
--xxx.100.12.5.1.1       
mirrorRspanVlan   OBJECT-TYPE
	SYNTAX      INTEGER 
        MAX-ACCESS  read-only
        STATUS      current
        DESCRIPTION "Vlan ID."
        ::= { mirrorRspanVlanEntry 1 } 

--xxx.100.12.5.1.2       
mirrorRspanVlanStatus   OBJECT-TYPE
	SYNTAX      INTEGER
		    {
            	    
               		active(1),
               		destroy(2)		    	
		    }	
        MAX-ACCESS  read-create
        STATUS      current
        DESCRIPTION "Vlan status."
        ::= { mirrorRspanVlanEntry 2 }     


--********************************************************************************************************
 
--xxx.100.12.6
mirrorRspanSessionTable OBJECT-TYPE 
    SYNTAX  SEQUENCE OF MirrorRspanSessionEntry
    MAX-ACCESS  not-accessible
    STATUS  current
    DESCRIPTION
        "Session configuration Table of Rspan.When creating an entry, 
        the correctness of both the Vlan ID an the Session ID should be ensured.
        When destroying an entry, only the correctness of the Session ID is required."
    ::= { primirror   6}
 
--xxx.100.12.6.1
mirrorRspanSessionEntry OBJECT-TYPE
        SYNTAX  MirrorRspanSessionEntry
        MAX-ACCESS  not-accessible
        STATUS  current
        DESCRIPTION
            "Session configuration of Rspan."
        INDEX   { mirrorRspanSession, mirrorRspanSessionVlan }
        ::= { mirrorRspanSessionTable 1 }

MirrorRspanSessionEntry
        ::= SEQUENCE
            { 
                mirrorRspanSession                  INTEGER,          
                mirrorRspanSessionVlan              INTEGER,               
                mirrorRspanSessionStatus            INTEGER
            }                

--xxx.100.12.6.1.1  
mirrorRspanSession   OBJECT-TYPE
	SYNTAX      INTEGER (1..4)	
        MAX-ACCESS  read-only
        STATUS      current
        DESCRIPTION "Session ID."
        ::= { mirrorRspanSessionEntry 1 }        
              
--xxx.100.12.6.1.2       
mirrorRspanSessionVlan   OBJECT-TYPE
	SYNTAX      INTEGER 
        MAX-ACCESS  read-only
        STATUS      current
        DESCRIPTION "Vlan ID."
        ::= { mirrorRspanSessionEntry 2 } 
        
--xxx.100.12.6.1.3       
mirrorRspanSessionStatus  OBJECT-TYPE
	SYNTAX      INTEGER
		    {
            	    
               		active(1),
               		destroy(2)		    	
		    }	
        MAX-ACCESS  read-create
        STATUS      current
        DESCRIPTION "The configuration status of the mirror session and its associated Rspan Vlan."
        ::= { mirrorRspanSessionEntry 3 }             
--********************************************************************************************************                                     
--xxx.100.12.7
mirrorDestGreTable OBJECT-TYPE 
    SYNTAX  SEQUENCE OF MirrorDestGreEntry
    MAX-ACCESS  not-accessible
    STATUS  current
    DESCRIPTION
        "Destination port for mirrored packets."
    ::= { primirror   7}
            
--xxx.100.12.7.1
mirrorDestGreEntry OBJECT-TYPE
        SYNTAX  MirrorDestGreEntry
        MAX-ACCESS  not-accessible
        STATUS  current
        DESCRIPTION
            "Destination port for mirrored packets."
        INDEX   { mirrorDestGreSession, mirrorDestGrePort}
        ::= { mirrorDestGreTable 1 }

MirrorDestGreEntry
        ::= SEQUENCE
            {
                mirrorDestGreSession       INTEGER,
                mirrorDestGrePort	   INTEGER,
                mirrorDestMacAddr          MacAddress,
                mirrorDestIP               IpAddress,
                mirrorSrcIP                IpAddress,
                mirrorDestGreStatus	   INTEGER
            }
            
--xxx.100.12.7.1.1       
mirrorDestGreSession   OBJECT-TYPE
	SYNTAX      INTEGER (1..4)	
        MAX-ACCESS  read-only
        STATUS      current
        DESCRIPTION "Session ID."
        ::= { mirrorDestGreEntry 1 } 
          
--xxx.100.12.7.1.2       
mirrorDestGrePort   OBJECT-TYPE
SYNTAX      INTEGER 	
        MAX-ACCESS  read-only
        STATUS      current
        DESCRIPTION "configure GRE port index."
        ::= { mirrorDestGreEntry 2 }  
--xxx.100.12.7.1.3      
mirrorDestMacAddr   OBJECT-TYPE
	SYNTAX      MacAddress		
        MAX-ACCESS  read-create
        STATUS      current
        DESCRIPTION "MAC address of equipment contacted with destination inferface."
        ::= { mirrorDestGreEntry 3 }  
--xxx.100.12.7.1.4    
mirrorDestIP   OBJECT-TYPE
	SYNTAX      IpAddress		
        MAX-ACCESS  read-create
        STATUS      current
        DESCRIPTION "GRE destination IP address."
        ::= { mirrorDestGreEntry 4 }  
--xxx.100.12.7.1.5       
mirrorSrcIP   OBJECT-TYPE
	SYNTAX      IpAddress		
        MAX-ACCESS  read-create
        STATUS      current
        DESCRIPTION "GRE source IP address."
        ::= { mirrorDestGreEntry 5 }  
--xxx.100.12.7.1.6       
mirrorDestGreStatus   OBJECT-TYPE
	SYNTAX      INTEGER
		    {
            	    
               		active(1),
               		destroy(2)		    	
		    }		
        MAX-ACCESS  read-create
        STATUS      current
        DESCRIPTION "Status."
        ::= { mirrorDestGreEntry 6 }                                              	                                     
--********************************************************************************************************
--xxx.100.13.1 
    dhcpRelay                     OBJECT IDENTIFIER ::= { pridhcp 1 }

--xxx.100.13.1.1
        dhcpRelayForwardUdpBootps OBJECT-TYPE
            SYNTAX  INTEGER
                {
                    noBootps(0),
                    bootps(1)
                }
            MAX-ACCESS  read-create
            STATUS  current
            DESCRIPTION "If dhcp rely forward bootps udp broadcast packet,broadcast message bootps."
            ::= { dhcpRelay 1 } 

--xxx.100.13.1.2
dhcpRelayServerAddrTable OBJECT-TYPE
          SYNTAX      SEQUENCE OF DhcpRelayServerAddrEntry
          MAX-ACCESS  not-accessible
          STATUS      current
          DESCRIPTION "The role of DHCP Relay Agent is to forward requests 
                        and replies between server and client when they are not
                        in the same subnet. To enable DHCP Relay service user needs to 
                        specify Relay Server ip address and then restart DHCP Relay.
                        This Table is to specify Relay Server ip address, 
                        the maximum numbers of server ip address user can specify is 5.
                        To Restart DHCP Relay, please use the dhcpRelayRestart variable."
          ::= { dhcpRelay 2 }
          
--xxx.100.13.1.2.1
dhcpRelayServerAddrEntry OBJECT-TYPE
          SYNTAX      DhcpRelayServerAddrEntry
          MAX-ACCESS  not-accessible
          STATUS      current
          DESCRIPTION "A conceptual row of dhcpRelayServerAddrTable."
          INDEX { dhcpRelayServerAddrVlanId , dhcpRelayServerAddrIndex } 
          ::= { dhcpRelayServerAddrTable 1 }
          
DhcpRelayServerAddrEntry ::= SEQUENCE
{
     dhcpRelayServerAddrVlanId  INTEGER,
     dhcpRelayServerAddrIndex    INTEGER,
     dhcpRelayServerAddrServerIp IpAddress,
     dhcpRelayServerAddrStatus   INTEGER    
}

--xxx.100.13.1.2.1.1
dhcpRelayServerAddrVlanId OBJECT-TYPE
          SYNTAX      INTEGER
          MAX-ACCESS  not-accessible
          STATUS      current
          DESCRIPTION "The ID of VLAN interface used by this table entry."
          ::= { dhcpRelayServerAddrEntry 1 }       

--xxx.100.13.1.2.1.2
dhcpRelayServerAddrIndex OBJECT-TYPE
          SYNTAX      INTEGER
          MAX-ACCESS  not-accessible
          STATUS      current
          DESCRIPTION "The index of relay address set in the VLAN interface."
          ::= { dhcpRelayServerAddrEntry 2 }  

--xxx.100.13.1.2.1.3
dhcpRelayServerAddrServerIp OBJECT-TYPE
          SYNTAX      IpAddress
          MAX-ACCESS  read-write
          STATUS      current
          DESCRIPTION "Appoint the destination address used for DHCP relay."
          ::= { dhcpRelayServerAddrEntry 3 }  

--xxx.100.13.1.2.1.4
dhcpRelayServerAddrStatus OBJECT-TYPE
          SYNTAX      INTEGER
              {
                  active(1),
                  destroy(2)
              }
          MAX-ACCESS  read-write
          STATUS      current
          DESCRIPTION "Configuration status."
          ::= { dhcpRelayServerAddrEntry 4 }  		
			
--xxx.100.13.1.3
        dhcpRelayOption82Enalbe OBJECT-TYPE
            SYNTAX  INTEGER
                {
                    noEnable(0),
                    enable(1)
                }
            MAX-ACCESS  read-create
            STATUS  current
            DESCRIPTION "If set(0), disable dhcp relay option82 function,
                        set(1),then enable dhcp relay option82 function."
            ::= { dhcpRelay 3 } 

--xxx.100.13.1.4
        dhcpRelayInformationOptionRemoteIDFormat OBJECT-TYPE
            SYNTAX  INTEGER
                {
                    default(0),
                    vs-hp(1)
                }
            MAX-ACCESS  read-create
            STATUS  current
            DESCRIPTION "If set(0), then use vlan mac address as the default format, 
                         set(1), use vs-hp format to keep compatibility with HP."
            ::= { dhcpRelay 4 } 

--xxx.100.13.1.5
        dhcpRelayInformationOptionRemoteID OBJECT-TYPE
        SYNTAX      DisplayString(SIZE(1..32))
            MAX-ACCESS  read-create
            STATUS  current
            DESCRIPTION "If input the 'standard' string ,then use vlan mac address format for option82 sub-option 2, 
                         other strings are used as romote ID of option82 sub-option 2,
                         the default string is 'standard'."
            ::= { dhcpRelay 5 } 

--xxx.100.13.1.6
        dhcpRelayInformationOptionSubscriberIDFormat OBJECT-TYPE
            SYNTAX  INTEGER
                {
                    hex(0),
                    acsii(1),
                    vs-hp(2)
                }
            MAX-ACCESS  read-create
            STATUS  current
            DESCRIPTION "If set(0), then use hex format of vlan and mac address,
                         set(1), use ACSII format of vlan and mac address,
                         set(2), use vs-hp format to keep compatibility with HP,
                         the default value is set(1)."
            ::= { dhcpRelay 6 }

--xxx.100.13.1.7
        dhcpServerRelayInformationEnable OBJECT-TYPE
            SYNTAX  INTEGER
                {
                    noEnable(0),
                    enable(1)
                }
            MAX-ACCESS  read-create
            STATUS  current
            DESCRIPTION "If set(0), disable the option82 relay function on dhcp server, the dhcp server neglects the option82 information,
                         set(1), then enable the option82 relay function on dhcp server,then dhcp server starts to identify option82 information."
            ::= { dhcpRelay 7 } 

--xxx.100.13.1.8
        dhcpRelayInformationOptionDelimiter  OBJECT-TYPE
            SYNTAX  INTEGER
                {
                    colon(0),
                    dot(1),
                    slash(2),
                    space(3)
                }
            MAX-ACCESS  read-create
            STATUS  current
            DESCRIPTION "If set(0), then use colon to compart sub-option parameters,
                         set(1), use dot to compart sub-option parameters,
                         set(2), use slash to compart sub-option parameters,
                         set(3), use space to compart sub-option parameters,
                         the default value is set(2)."
            ::= { dhcpRelay 8 }	

--xxx.100.13.1.9
        dhcpRelayOptionSelfDefinedSubscriberIDFormat   OBJECT-TYPE
            SYNTAX  INTEGER
                {
                    hex(0),
                    ascii(1)
                }
            MAX-ACCESS  read-create
            STATUS  current
            DESCRIPTION "If set(0), then use hex format to generate sub-scriber ID,
                         set(1), use ASCII format to generate sub-scriber ID,
                         the default value is set(1)."
            ::= { dhcpRelay 9 }

--xxx.100.13.1.10
        dhcpRelayOptionSelfDefinedRemoteIDFormat   OBJECT-TYPE
            SYNTAX  INTEGER
                {
                    hex(0),
                    ascii(1)
                }
            MAX-ACCESS  read-create
            STATUS  current
            DESCRIPTION "If set(0), then use hex format to generate remote ID,
                         set(1), use ASCII format to generate remote ID,
                         the default value is set(1)."
            ::= { dhcpRelay 10 }	

--xxx.100.13.1.11
        dhcpRelayOptionSelfDefinedSubscriberID   OBJECT-TYPE
            SYNTAX  DisplayString(SIZE(1..128))
            MAX-ACCESS  read-create
            STATUS  current
            DESCRIPTION "If user does not configure the circuit-id of option82 explicitly on a port, then 
                         the user can self define format to generate the circuit-id, the format options include
                         vlan, port, ID, self-designed string, the subscriber ID may be only one or any combination of them,
                         and is strictly generated according to the sequence of format options, the ID option includes 	
                         switch ID and remote-mac, but the user just select only one of them, also In the swtich ID, it 
                         includes mac and hostname options, the user just select only one of two, the maximum length 
                         of self-designed striing is 64. If user input the string 'NULL', then delete the last configuration.
                         For example, if select vlan ,ID(swtich-id(mac)), and string 'str' format,
                         the user input the string like as 'vlan id swtich-id mac string str'."
            ::= { dhcpRelay 11 }

--xxx.100.13.1.12
        dhcpRelayOptionSelfDefinedRemoteID   OBJECT-TYPE
            SYNTAX  DisplayString(SIZE(1..64))
            MAX-ACCESS  read-create
            STATUS  current
            DESCRIPTION "If user does not configure the remote-id of option82 explicitly on a port, then 
                         the user can self define format to generate the remote-id, the format options include
                         mac,hostname and self-designed string, the remote ID may be only one or any combination of them,
                         and is strictly generated according to the sequence of format options, 
                         the maximum length of self-designed striing is 32.
                         If user input the string 'NULL', then delete the last configuration.
                         For example, if select hostname,mac,and string 'str' format,
                         the user input the string like as 'hostname mac string str'."
            ::= { dhcpRelay 12 }

--xxx.100.13.1.13
dhcpRelayOption82InterfaceConfigureTable OBJECT-TYPE
          SYNTAX      SEQUENCE OF DhcpRelayOption82InterfaceConfigureEntry
          MAX-ACCESS  not-accessible
          STATUS      current
          DESCRIPTION "After enable the option82 relay function ,the swith must adopt some forwarding policy,
                       and use specified format for subscriber ID to handle receving the dhcp request packets 
                       according to specified port."
          ::= { dhcpRelay 13 }

--xxx.100.13.1.13.1
dhcpRelayOption82InterfaceConfigureEntry OBJECT-TYPE
          SYNTAX      DhcpRelayOption82InterfaceConfigureEntry
          MAX-ACCESS  not-accessible
          STATUS      current
          DESCRIPTION "A conceptual row of dhcpRelayOption82InterfaceConfigureTable."
          INDEX { dhcpRelayOption82Vid } 
          ::= { dhcpRelayOption82InterfaceConfigureTable 1 }
          
DhcpRelayOption82InterfaceConfigureEntry ::= SEQUENCE
{
     dhcpRelayOption82Vid  INTEGER,
     dhcpRelayOption82ForwardPolicy   INTEGER,
     dhcpRelayOption82SubscriberID DisplayString   
}

--xxx.100.13.1.13.1.1
dhcpRelayOption82Vid OBJECT-TYPE
          SYNTAX      INTEGER
          MAX-ACCESS  not-accessible
          STATUS      current
          DESCRIPTION "The Vlan interface being used by this table entry. 
                       Only the Vlan interfaces which have an IP configured will appear in the table."
          ::= { dhcpRelayOption82InterfaceConfigureEntry 1 }       

--xxx.100.13.1.13.1.2
dhcpRelayOption82ForwardPolicy OBJECT-TYPE
          SYNTAX      INTEGER
              {
               	 drop(1),
               	 keep(2),
                 replace(3)
              }
          MAX-ACCESS  read-write
          STATUS      current
          DESCRIPTION "If set(1), then drop the dhcp request packets with option82 sub-option,
                       set(2), keep the dhcp request packets with option82 sub-option and forward to the dhcp server,
                       set(3), the systerm replace the option82 sub-option of dhcp request packets with its own option82 sub-option,
                       the default value is set(3)."
          ::= { dhcpRelayOption82InterfaceConfigureEntry 2 }  

--xxx.100.13.1.13.1.3
dhcpRelayOption82SubscriberID OBJECT-TYPE
          SYNTAX      DisplayString(SIZE(1..64))
          MAX-ACCESS  read-write
          STATUS      current
          DESCRIPTION "If input the 'standard' string ,then use vlan and physical port format for option82 sub-option 1, 
                       other string, that be used as circuit-id of option82 sub-option 1,
                       the default string is 'standard'."
          ::= { dhcpRelayOption82InterfaceConfigureEntry 3 }    
		  
--xxx.100.13.1.14
dhcpRelaySharevlanSubvlanConfigureTable OBJECT-TYPE
          SYNTAX      SEQUENCE OF DhcpRelaySharevlanSubvlanConfigureEntry
          MAX-ACCESS  not-accessible
          STATUS      current
          DESCRIPTION "the swith use the subvlan 
						to handle receving the dhcp request packets."
          ::= { dhcpRelay 14 }

--xxx.100.13.1.14.1
dhcpRelaySharevlanSubvlanConfigureEntry OBJECT-TYPE
          SYNTAX      DhcpRelaySharevlanSubvlanConfigureEntry
          MAX-ACCESS  not-accessible
          STATUS      current
          DESCRIPTION "A conceptual row of dhcpRelaySharevlanSubvlanConfigureTable."
          INDEX { dhcpRelaySharevlanSubvlanList } 
          ::= { dhcpRelaySharevlanSubvlanConfigureTable 1 }
          
DhcpRelaySharevlanSubvlanConfigureEntry ::= SEQUENCE
{
		dhcpRelaySharevlanSubvlanList OCTET STRING,
		dhcpRelayNoSharevlan INTEGER	 
}

--xxx.100.13.1.14.1.1
dhcpRelaySharevlanSubvlanList OBJECT-TYPE
          SYNTAX      OCTET STRING(SIZE(0..64))
          MAX-ACCESS  read-write
          STATUS      current
          DESCRIPTION "DHCP Relay: set the subvlan list for the sharevlan."
          ::= { dhcpRelaySharevlanSubvlanConfigureEntry 1 }  
--xxx.100.13.1.14.1.2
dhcpRelayNoSharevlan OBJECT-TYPE
          SYNTAX      INTEGER{
				disable(0)
          }
          MAX-ACCESS  read-write
          STATUS      current
          DESCRIPTION "DHCP Relay: UNset the subvlan list for the sharevlan."
          ::= { dhcpRelaySharevlanSubvlanConfigureEntry 2 } 		  
--********************************************************************************************************

--xxx.100.13.2 
    dhcpServer                     OBJECT IDENTIFIER ::= { pridhcp 2 }

--xxx.100.13.2.1
        dhcpServerServiceStatus OBJECT-TYPE
            SYNTAX  INTEGER
            	    {
                        enable(1),
                        disable(0)
                    }
            MAX-ACCESS  read-create
            STATUS  current
            DESCRIPTION
                "Setting this to 1 to enable the dhcp server service.
                 Setting this to 2 to disable the dhcp server service."
            ::= { dhcpServer 1 } 
            
--xxx.100.13.2.2
        dhcploggingStatus OBJECT-TYPE
            SYNTAX  INTEGER
            	    {
                        enable(1),
                        disable(0)
                    }
            MAX-ACCESS  read-create
            STATUS  current
            DESCRIPTION
                "Setting this to 1 to enable the dhcp conflict logging. 
                 Setting this to 0 to disable the dhcp conflict logging."
            ::= { dhcpServer 2 } 
--********************************************************************************************************]

--xxx.100.13.2.3
    dhcpPool               		  OBJECT IDENTIFIER ::= { dhcpServer 3 }         
    
                     
--********************************************************************************************************

--xxx.100.13.2.3.1
dhcpPoolTable OBJECT-TYPE
          SYNTAX      SEQUENCE OF DhcpPoolEntry
          MAX-ACCESS  not-accessible
          STATUS      current
          DESCRIPTION "A dhcp pool is a collection of
                       user configuration such as option config-lease time                         
                        or dns-server IPs, a network address for network pool,
                        or a host IP plus a hardware address pair for host pool. 
                        However, a dhcp pool only can either be a network pool 
                        or a host pool, or none of them (such as that pool only 
                        containing option config no network address config 
                        or a host ip config as well)"
          ::= { dhcpPool 1 }
          
--xxx.100.13.2.3.1.1
dhcpPoolEntry OBJECT-TYPE
          SYNTAX      DhcpPoolEntry
          MAX-ACCESS  not-accessible
          STATUS      current
          DESCRIPTION "A conceptual row of dhcpPoolTable."
          INDEX { dhcpPoolPoolName }
          ::= { dhcpPoolTable 1 }

DhcpPoolEntry ::= SEQUENCE
{
     dhcpPoolPoolName  			DisplayString,
     dhcpPoolStatus 			INTEGER,
     dhcpPoolAddressType		INTEGER,
     dhcpPoolAddress  			IpAddress,
     dhcpPoolAddressPrefix 		IpAddress,
     dhcpPoolAddressStatus		INTEGER,
     dhcpPoolMacAddress 		DisplayString,
     dhcpPoolProType 			INTEGER,
     dhcpPoolMacStatus			INTEGER
}

--xxx.100.13.2.3.1.1.1
dhcpPoolPoolName OBJECT-TYPE
          SYNTAX      DisplayString(SIZE(1..32))
          MAX-ACCESS  not-accessible
          STATUS      current
          DESCRIPTION "PoolName, simply specify a string."
          ::= { dhcpPoolEntry 1 }  
          
--xxx.100.13.2.3.1.1.2          
dhcpPoolStatus OBJECT-TYPE
          SYNTAX      INTEGER
            	    {
               		active(1),
               		destroy(0)
            	    }  
          MAX-ACCESS  read-create
          STATUS      current
          DESCRIPTION "accession delete the pool,according to dhcpPoolName"
          ::= { dhcpPoolEntry 2 }  

--xxx.100.13.2.3.1.1.3          
dhcpPoolAddressType OBJECT-TYPE
          SYNTAX      INTEGER
            	    {
               		network(1),
               		host(2)
            	    }  
          MAX-ACCESS  read-create
          STATUS      current
          DESCRIPTION "configure dhcppool of address style"
          ::= { dhcpPoolEntry 3 }  
                                 
--xxx.100.13.2.3.1.1.4  
dhcpPoolAddress OBJECT-TYPE
          SYNTAX      IpAddress
          MAX-ACCESS  read-create
          STATUS      current
          DESCRIPTION "configurate dhcp pool.
           if dhcpPoolAddressType=1 configurate address range,
		       if dhcpPoolAddressType=2 configurate single address"
          ::= { dhcpPoolEntry 4 }  

--xxx.100.13.2.3.1.1.5
dhcpPoolAddressPrefix OBJECT-TYPE
          SYNTAX      IpAddress
          MAX-ACCESS  read-create
          STATUS      current
          DESCRIPTION "dhcp pool ip address prefix"
          ::= { dhcpPoolEntry 5 }  

--xxx.100.13.2.3.1.1.6          
dhcpPoolAddressStatus OBJECT-TYPE
          SYNTAX    INTEGER
            	    {
               		active(1),
               		destroy(0)
            	    }           
          MAX-ACCESS  read-create
          STATUS      current
          DESCRIPTION "address of configuration satus"
          ::= { dhcpPoolEntry 6 }    

--xxx.100.13.2.3.1.1.7
dhcpPoolMacAddress OBJECT-TYPE
          SYNTAX      DisplayString
          MAX-ACCESS  read-create
          STATUS      current
          DESCRIPTION "appoint user of hardware address.Condition: dhcpPoolAddressType(2)."
          ::= { dhcpPoolEntry 7 }  
          
--xxx.100.13.2.3.1.1.8          
dhcpPoolProType OBJECT-TYPE
          SYNTAX      INTEGER(1..255)
          MAX-ACCESS  read-create
          STATUS      current
          DESCRIPTION "RFC define protocol style of number express,Condition:dhcpPoolAddressType(2)."
          ::= { dhcpPoolEntry 8 } 
 
--xxx.100.13.2.3.1.1.9          
dhcpPoolMacStatus OBJECT-TYPE
          SYNTAX    INTEGER
            	    {
               		active(1),
               		destroy(0)
            	    }           
          MAX-ACCESS  read-create
          STATUS      current
          DESCRIPTION "hardware address configure status.Condition: dhcpPoolAddressType(2)."
          ::= { dhcpPoolEntry 9 }         
          
                                      
--********************************************************************************************************                                     
  
--xxx.100.13.2.3.2
dhcpPoolExpandTable OBJECT-TYPE
          SYNTAX      SEQUENCE OF DhcpPoolExpandEntry
          MAX-ACCESS  not-accessible
          STATUS      current
          DESCRIPTION "A dhcp pool is a collection of
                       user configuration such as option config-lease time                         
                        or dns-server IPs, a network address for network pool,
                        or a host IP plus a hardware address pair for host pool. 
                        However, a dhcp pool only can either be a network pool 
                        or a host pool, or none of them (such as that pool only 
                        containing option config no network address config 
                        or a host ip config as well)"
          ::= { dhcpPool 2 }
          
--xxx.100.13.2.3.2.1
dhcpPoolExpandEntry OBJECT-TYPE
          SYNTAX      DhcpPoolExpandEntry
          MAX-ACCESS  not-accessible
          STATUS      current
          DESCRIPTION "A conceptual row of dhcpPoolExpandTable."
          INDEX { dhcpPoolExpandName }
          ::= { dhcpPoolExpandTable 1 }

DhcpPoolExpandEntry ::= SEQUENCE
{
     dhcpPoolExpandName  		DisplayString,
     dhcpPoolNetbiosNodeType		INTEGER,
     dhcpPoolDomainName			DisplayString,
     dhcpPoolBootFile			DisplayString,
     dhcpPoolCLid			DisplayString,
--     dhcpPoolCLname			DisplayString,
     dhcpPoolExpandstatus		INTEGER
}                                 
 
--xxx.100.13.2.3.2.1.1
dhcpPoolExpandName OBJECT-TYPE
          SYNTAX      DisplayString(SIZE(1..32))
          MAX-ACCESS  not-accessible
          STATUS      current
          DESCRIPTION "PoolName, simply specify a string which 
                      string size NO MORE THAN 8"
          ::= { dhcpPoolExpandEntry 1 } 
      
                    
--xxx.100.13.2.3.2.1.2         
dhcpPoolNetbiosNodeType OBJECT-TYPE
          SYNTAX      INTEGER(0..255)
          MAX-ACCESS  read-create
          STATUS      current
          DESCRIPTION "Configure DHCP client of node style. 
                      For example, Broadcast node 1, Peer-to-peer node 2, Mixed node 4, Hybrid node 8"
          ::= { dhcpPoolExpandEntry 2 }                     

--xxx.100.13.2.3.2.1.3         
dhcpPoolDomainName OBJECT-TYPE
          SYNTAX      DisplayString(SIZE(1..255))
          MAX-ACCESS  read-create
          STATUS      current
          DESCRIPTION "DHCP client configure domain name"
          ::= { dhcpPoolExpandEntry 3 }  

--xxx.100.13.2.3.2.1.4         
dhcpPoolBootFile OBJECT-TYPE
          SYNTAX      DisplayString(SIZE(1..255))
          MAX-ACCESS  read-create
          STATUS      current
          DESCRIPTION "configure DHCP client boot-file name"
          ::= { dhcpPoolExpandEntry 4 }
          
--xxx.100.13.2.3.2.1.5        
dhcpPoolCLid OBJECT-TYPE
          SYNTAX      DisplayString
          MAX-ACCESS  read-create
          STATUS      current
          DESCRIPTION "set dhcp pool client id.
		       Condition: the pool of address is handcraft bind"
          ::= { dhcpPoolExpandEntry 5 }
          
--xxx.100.13.2.3.2.1.6          
--dhcpPoolCLname OBJECT-TYPE
--          SYNTAX      DisplayString(SIZE(1..255))
--          MAX-ACCESS  read-create
--          STATUS      current
--          DESCRIPTION "configure user name.
--		       Condition: the pool address is handcraft bind."
--          ::= { dhcpPoolExpandEntry 6 }  
                
--xxx.100.13.2.3.2.1.7        
dhcpPoolExpandstatus OBJECT-TYPE
          SYNTAX    INTEGER
            	    {
               		valid(0),
               		destroy(1)
            	    }           
          MAX-ACCESS  read-create
          STATUS      current
          DESCRIPTION "if configure is valid(0),and the list of all configuration operatation accession 
		       if configure is destroy(1),and the list of all configuration operation delet"
          ::= { dhcpPoolExpandEntry 7 }               
                                                         
--********************************************************************************************************       
      
--xxx.100.13.2.3.2.1.2
dhcpLeaseTimeTable OBJECT-TYPE
          SYNTAX      SEQUENCE OF DhcpLeaseTimeEntry
          MAX-ACCESS  not-accessible
          STATUS      current
          DESCRIPTION "configure rent term in address pool"
          ::= { dhcpServer 4 }
          
--xxx.100.13.2.4.1
dhcpLeaseTimeEntry OBJECT-TYPE
          SYNTAX      DhcpLeaseTimeEntry
          MAX-ACCESS  not-accessible
          STATUS      current
          DESCRIPTION "configure rent term in address pool"
          INDEX { dhcpLeaseTimePoolName }
          ::= { dhcpLeaseTimeTable 1 }

DhcpLeaseTimeEntry ::= SEQUENCE
{
     dhcpLeaseTimePoolName  		DisplayString,
     dhcpLeaseTimeType 			INTEGER,
     dhcpLeaseTimeDay  			INTEGER,
     dhcpLeaseTimeHours 		INTEGER,
     dhcpLeaseTimeMinutes 		INTEGER,
     dhcpLeaseTimeStatus 		INTEGER
}

--xxx.100.13.2.4.1.1
dhcpLeaseTimePoolName OBJECT-TYPE
          SYNTAX      DisplayString(SIZE(1..32))
          MAX-ACCESS  not-accessible
          STATUS      current
          DESCRIPTION "PoolName, simply specify a string which 
                      string size NO MORE THAN 8"
          ::= { dhcpLeaseTimeEntry 1 }            
          
--xxx.100.13.2.4.1.2
dhcpLeaseTimeType  OBJECT-TYPE
          SYNTAX      INTEGER
          	      {
          	      	temp(0),
          	      	infinite(1)
          	      }
          MAX-ACCESS  read-create
          STATUS      current
          DESCRIPTION "rent time style,0 is temporarily rent,1 is forever rent"
          ::= { dhcpLeaseTimeEntry 2 }     

--xxx.100.13.2.4.1.3
dhcpLeaseTimeDay  OBJECT-TYPE
          SYNTAX      INTEGER(0..365)
          MAX-ACCESS  read-create
          STATUS      current
          DESCRIPTION "day,condition:dhcpLeaseTimeType=temp(0)."
          ::= { dhcpLeaseTimeEntry 3 }  
          
--xxx.100.13.2.4.1.4
dhcpLeaseTimeHours  OBJECT-TYPE
          SYNTAX      INTEGER(0..23)
          MAX-ACCESS  read-create
          STATUS      current
          DESCRIPTION "hour,condition:dhcpLeaseTimeType=temp(0)."
          ::= { dhcpLeaseTimeEntry 4 }           
          
--xxx.100.13.2.4.1.5
dhcpLeaseTimeMinutes  OBJECT-TYPE
          SYNTAX      INTEGER(0..59)
          MAX-ACCESS  read-create
          STATUS      current
          DESCRIPTION "hour,condition:dhcpLeaseTimeType=temp(0)."
          ::= { dhcpLeaseTimeEntry 5 }  
          
--xxx.100.13.2.4.1.6A
dhcpLeaseTimeStatus  OBJECT-TYPE
          SYNTAX    INTEGER
            	    {
            	    	createAndGo(0),
               		active(1),
               		destroy(2)
            	    }          
          MAX-ACCESS  read-create
          STATUS      current
          DESCRIPTION "Setting this to active(1) creates an entry.
                       Setting this to destroy(2) destroys an entry.
		       default status is 0,no opperation"
          ::= { dhcpLeaseTimeEntry 6 }   
                                                                  
--********************************************************************************************************          

--xxx.100.13.2.5
dhcpPoolOptionTable OBJECT-TYPE
          SYNTAX      SEQUENCE OF DhcpPoolOptionEntry
          MAX-ACCESS  not-accessible
          STATUS      current
          DESCRIPTION "configure pool of optional parameters"
          ::= { dhcpServer 5 }
          
--xxx.100.13.2.5.1
dhcpPoolOptionEntry OBJECT-TYPE
          SYNTAX      DhcpPoolOptionEntry
          MAX-ACCESS  not-accessible
          STATUS      current
          DESCRIPTION "configure pool of optional parameters"
          INDEX { dhcpPoolOptionName, dhcpPoolOptionIndex }
          ::= { dhcpPoolOptionTable 1 }

DhcpPoolOptionEntry ::= SEQUENCE
{
     dhcpPoolOptionName  	DisplayString,
     dhcpPoolOptionIndex	INTEGER,
     dhcpPoolOptionId 		INTEGER,
     dhcpPoolOptionType  	INTEGER,
     dhcpPoolOption 		DisplayString,
     dhcpPoolOptionStatus 	INTEGER
}

--xxx.100.13.2.5.1.1
dhcpPoolOptionName OBJECT-TYPE
          SYNTAX      DisplayString(SIZE(1..32))
          MAX-ACCESS  not-accessible
          STATUS      current
          DESCRIPTION "PoolName, simply specify a string which 
                      string size NO MORE THAN 8"
          ::= { dhcpPoolOptionEntry 1 }     

--xxx.100.13.2.5.1.2
dhcpPoolOptionIndex OBJECT-TYPE
          SYNTAX      INTEGER
          MAX-ACCESS  not-accessible
          STATUS      current
          DESCRIPTION "The index of option which has been set in this pool"
          ::= { dhcpPoolOptionEntry 2 } 

--xxx.100.13.2.5.1.3
dhcpPoolOptionId OBJECT-TYPE
          SYNTAX      INTEGER(0..254)
          MAX-ACCESS  read-create
          STATUS      current
          DESCRIPTION "dhcpPoolOptionId (0..254)"
          ::= { dhcpPoolOptionEntry 3 }   

--xxx.100.13.2.5.1.4
dhcpPoolOptionType OBJECT-TYPE
          SYNTAX      INTEGER
            	    {
            	    	ascii(1),
               		hex(2),
               		ipaddress(3)
            	    }
          MAX-ACCESS  read-create
          STATUS      current
          DESCRIPTION "dhcpPoolOptionType"
          ::= { dhcpPoolOptionEntry 4 }   

--xxx.100.13.2.5.1.5
dhcpPoolOption OBJECT-TYPE
          SYNTAX      DisplayString
          MAX-ACCESS  read-create
          STATUS      current
          DESCRIPTION "
           if dhcpPoolOptionType=1, ASCII string
		       if dhcpPoolOptionType=2, HEX string
		       if dhcpPoolOptionType=3,IP address"
          ::= { dhcpPoolOptionEntry 5 }             

--xxx.100.13.2.5.1.6
dhcpPoolOptionStatus OBJECT-TYPE
          SYNTAX    INTEGER
            	    {
            	    	createAndGo(0),
               		active(1),
               		destroy(2)
            	    } 
          MAX-ACCESS  read-create
          STATUS      current
          DESCRIPTION "optional parameters configure status"
          ::= { dhcpPoolOptionEntry 6 }            
                                                                            
--********************************************************************************************************

--xxx.100.13.2.6
dhcpServerExcludedIpAddrTable OBJECT-TYPE
          SYNTAX      SEQUENCE OF DhcpServerExcludedIpAddrEntry
          MAX-ACCESS  not-accessible
          STATUS      current
          DESCRIPTION "dhcpServer Excluded IpAddr Table"
          ::= { dhcpServer 6 }
          
--xxx.100.13.2.6.1
dhcpServerExcludedIpAddrEntry OBJECT-TYPE
          SYNTAX      DhcpServerExcludedIpAddrEntry
          MAX-ACCESS  not-accessible
          STATUS      current
          DESCRIPTION "dhcpServer Excluded IpAddrEntry"
          INDEX { dhcpServerExcludedIpAddrLowIp , dhcpServerExcludedIpAddrHiIp }
          ::= { dhcpServerExcludedIpAddrTable 1 }

DhcpServerExcludedIpAddrEntry ::= SEQUENCE
{
     dhcpServerExcludedIpAddrLowIp  	IpAddress,
     dhcpServerExcludedIpAddrHiIp 	IpAddress,
     dhcpServerExcludedIpAddrStatus  	INTEGER
}

--xxx.100.13.2.6.2
dhcpServerExcludedIpAddrLowIp OBJECT-TYPE
          SYNTAX      IpAddress
          MAX-ACCESS  not-accessible
          STATUS      current
          DESCRIPTION "The excluded IP address, 
                        or first IP address in an excluded address range."
          ::= { dhcpServerExcludedIpAddrEntry 1 }  
                
--xxx.100.13.2.6.3
dhcpServerExcludedIpAddrHiIp OBJECT-TYPE
          SYNTAX      IpAddress
          MAX-ACCESS  not-accessible
          STATUS      current
          DESCRIPTION "The last IP address in the excluded address range."
          ::= { dhcpServerExcludedIpAddrEntry 2 }   

--xxx.100.13.2.6.4
dhcpServerExcludedIpAddrStatus OBJECT-TYPE
          SYNTAX    INTEGER
            	    {
            	    	createAndGo(0),
               		active(1),
               		destroy(2)
            	    } 
          MAX-ACCESS  read-create
          STATUS      current
          DESCRIPTION "Setting this to active(1) creates an entry.
                       Setting this to destroy(2) destroys an entry."
          ::= { dhcpServerExcludedIpAddrEntry 3 } 

--********************************************************************************************************

--xxx.100.13.2.8
dhcpPoolDnsSerTable OBJECT-TYPE
          SYNTAX      SEQUENCE OF DhcpPoolDnsSerEntry
          MAX-ACCESS  not-accessible
          STATUS      current
          DESCRIPTION " dhcpPool Dns Server Table:the maximum 8 dns is allowed
			the first dns server has the highest priority.so address1 is highest priority,next is address2,address3..."
          ::= { dhcpServer 8 }
          
--xxx.100.13.2.8.1
dhcpPoolDnsSerEntry OBJECT-TYPE
          SYNTAX      DhcpPoolDnsSerEntry
          MAX-ACCESS  not-accessible
          STATUS      current
          DESCRIPTION "is DHCP client configure DNS server"
          INDEX { dhcpPoolDnsSerPoolName }
          ::= { dhcpPoolDnsSerTable 1 }

DhcpPoolDnsSerEntry ::= SEQUENCE
{
     dhcpPoolDnsSerPoolName  	DisplayString,
     dhcpPoolDnsSerIpAddress1 	IpAddress,
     dhcpPoolDnsSerIpAddress2  	IpAddress,
     dhcpPoolDnsSerIpAddress3	IpAddress,
     dhcpPoolDnsSerIpAddress4	IpAddress,
     dhcpPoolDnsSerIpAddress5	IpAddress,
     dhcpPoolDnsSerIpAddress6	IpAddress,
     dhcpPoolDnsSerIpAddress7	IpAddress,
     dhcpPoolDnsSerIpAddress8	IpAddress,
     dhcpPoolDnsSerStatus	INTEGER
}

--xxx.100.13.2.8.1
dhcpPoolDnsSerPoolName OBJECT-TYPE
          SYNTAX      DisplayString
          MAX-ACCESS  not-accessible
          STATUS      current
          DESCRIPTION "PoolName, simply specify a string which 
                      string size NO MORE THAN 8"
          ::= { dhcpPoolDnsSerEntry 1 } 
          
--xxx.100.13.2.8.2
dhcpPoolDnsSerIpAddress1 OBJECT-TYPE
          SYNTAX      IpAddress
          MAX-ACCESS  read-create
          STATUS      current
          DESCRIPTION "IP address,MUST."
          ::= { dhcpPoolDnsSerEntry 2 }          
          
--xxx.100.13.2.8.3
dhcpPoolDnsSerIpAddress2 OBJECT-TYPE
          SYNTAX      IpAddress
          MAX-ACCESS  read-create
          STATUS      current
          DESCRIPTION "IP address,option"
          ::= { dhcpPoolDnsSerEntry 3 }          
          
--xxx.100.13.2.8.4
dhcpPoolDnsSerIpAddress3 OBJECT-TYPE
          SYNTAX      IpAddress
          MAX-ACCESS  read-create
          STATUS      current
          DESCRIPTION "IP address,option"
          ::= { dhcpPoolDnsSerEntry 4 }          
          
--xxx.100.13.2.8.5
dhcpPoolDnsSerIpAddress4 OBJECT-TYPE
          SYNTAX      IpAddress
          MAX-ACCESS  read-create
          STATUS      current
          DESCRIPTION "IP address,option"
          ::= { dhcpPoolDnsSerEntry 5 }          
          
--xxx.100.13.2.8.6
dhcpPoolDnsSerIpAddress5 OBJECT-TYPE
          SYNTAX      IpAddress
          MAX-ACCESS  read-create
          STATUS      current
          DESCRIPTION "IP address,option"
          ::= { dhcpPoolDnsSerEntry 6 }          
          
--xxx.100.13.2.8.7
dhcpPoolDnsSerIpAddress6 OBJECT-TYPE
          SYNTAX      IpAddress
          MAX-ACCESS  read-create
          STATUS      current
          DESCRIPTION "IP address,option"
          ::= { dhcpPoolDnsSerEntry 7 }          
          
--xxx.100.13.2.8.8
dhcpPoolDnsSerIpAddress7 OBJECT-TYPE
          SYNTAX      IpAddress
          MAX-ACCESS  read-create
          STATUS      current
          DESCRIPTION "IP address,option"
          ::= { dhcpPoolDnsSerEntry 8 }          

--xxx.100.13.2.8.9
dhcpPoolDnsSerIpAddress8 OBJECT-TYPE
          SYNTAX      IpAddress
          MAX-ACCESS  read-create
          STATUS      current
          DESCRIPTION "IP address,option"
          ::= { dhcpPoolDnsSerEntry 9 }  

--xxx.100.13.2.8.10
dhcpPoolDnsSerStatus OBJECT-TYPE
          SYNTAX    INTEGER
            	    {
            	    	createAndGo(0),
               		active(1),
               		destroy(2)
            	    } 
          MAX-ACCESS  read-create
          STATUS      current
          DESCRIPTION "configure DNS server status"
          ::= { dhcpPoolDnsSerEntry 10 }            
          
--********************************************************************************************************


--xxx.100.13.2.9
dhcpPoolDefaultRouterTable OBJECT-TYPE
          SYNTAX      SEQUENCE OF DhcpPoolDefaultRouterEntry
          MAX-ACCESS  not-accessible
          STATUS      current
          DESCRIPTION "dhcpPoolDefaultRouterTable:
          the maximum 8 default gateway address can be set,the first gateway has the highest priority,
          So address1 has the highest priority,next is address2,address3..."
          ::= { dhcpServer 9 }
          
--xxx.100.13.2.9.1
dhcpPoolDefaultRouterEntry OBJECT-TYPE
          SYNTAX      DhcpPoolDefaultRouterEntry
          MAX-ACCESS  not-accessible
          STATUS      current
          DESCRIPTION "DHCP client machine configure default gateway"
          INDEX { dhcpPoolDnsSerPoolName }
          ::= { dhcpPoolDefaultRouterTable 1 }

DhcpPoolDefaultRouterEntry ::= SEQUENCE
{
     dhcpPoolDefaultRouterPoolName  	DisplayString,
     dhcpPoolDefaultRouterIpAddress1 	IpAddress,
     dhcpPoolDefaultRouterIpAddress2  	IpAddress,
     dhcpPoolDefaultRouterIpAddress3	IpAddress,
     dhcpPoolDefaultRouterIpAddress4	IpAddress,
     dhcpPoolDefaultRouterIpAddress5	IpAddress,
     dhcpPoolDefaultRouterIpAddress6	IpAddress,
     dhcpPoolDefaultRouterIpAddress7	IpAddress,
     dhcpPoolDefaultRouterIpAddress8	IpAddress,
     dhcpPoolDefaultRouterStatus	INTEGER
}

--xxx.100.13.2.9.1
dhcpPoolDefaultRouterPoolName OBJECT-TYPE
          SYNTAX      DisplayString
          MAX-ACCESS  not-accessible
          STATUS      current
          DESCRIPTION "PoolName, simply specify a string which 
                      string size NO MORE THAN 8"
          ::= { dhcpPoolDefaultRouterEntry 1 } 
          
--xxx.100.13.2.9.2
dhcpPoolDefaultRouterIpAddress1 OBJECT-TYPE
          SYNTAX      IpAddress
          MAX-ACCESS  read-create
          STATUS      current
          DESCRIPTION "IP address,must"
          ::= { dhcpPoolDefaultRouterEntry 2 }          
          
--xxx.100.13.2.9.3
dhcpPoolDefaultRouterIpAddress2 OBJECT-TYPE
          SYNTAX      IpAddress
          MAX-ACCESS  read-create
          STATUS      current
          DESCRIPTION "IP address,option"
          ::= { dhcpPoolDefaultRouterEntry 3 }          
          
--xxx.100.13.2.9.4
dhcpPoolDefaultRouterIpAddress3 OBJECT-TYPE
          SYNTAX      IpAddress
          MAX-ACCESS  read-create
          STATUS      current
          DESCRIPTION "IP address,option"
          ::= { dhcpPoolDefaultRouterEntry 4 }          
          
--xxx.100.13.2.9.5
dhcpPoolDefaultRouterIpAddress4 OBJECT-TYPE
          SYNTAX      IpAddress
          MAX-ACCESS  read-create
          STATUS      current
          DESCRIPTION "IP address,option"
          ::= { dhcpPoolDefaultRouterEntry 5 }          
          
--xxx.100.13.2.9.6
dhcpPoolDefaultRouterIpAddress5 OBJECT-TYPE
          SYNTAX      IpAddress
          MAX-ACCESS  read-create
          STATUS      current
          DESCRIPTION "IP address,option"
          ::= { dhcpPoolDefaultRouterEntry 6 }          
          
--xxx.100.13.2.9.7
dhcpPoolDefaultRouterIpAddress6 OBJECT-TYPE
          SYNTAX      IpAddress
          MAX-ACCESS  read-create
          STATUS      current
          DESCRIPTION "IP address,option"
          ::= { dhcpPoolDefaultRouterEntry 7 }          
          
--xxx.100.13.2.8.8
dhcpPoolDefaultRouterIpAddress7 OBJECT-TYPE
          SYNTAX      IpAddress
          MAX-ACCESS  read-create
          STATUS      current
          DESCRIPTION "IP address,option"
          ::= { dhcpPoolDefaultRouterEntry 8 }          

--xxx.100.13.2.9.9
dhcpPoolDefaultRouterIpAddress8 OBJECT-TYPE
          SYNTAX      IpAddress
          MAX-ACCESS  read-create
          STATUS      current
          DESCRIPTION "IP address,option"
          ::= { dhcpPoolDefaultRouterEntry 9 }  

--xxx.100.13.2.9.10
dhcpPoolDefaultRouterStatus OBJECT-TYPE
          SYNTAX    INTEGER
            	    {
            	    	createAndGo(0),
               		active(1),
               		destroy(2)
            	    } 
          MAX-ACCESS  read-create
          STATUS      current
          DESCRIPTION "configure default gateway state machine"
          ::= { dhcpPoolDefaultRouterEntry 10 }  
--********************************************************************************************************


--xxx.100.13.2.10
dhcpPoolNextServerTable OBJECT-TYPE
          SYNTAX      SEQUENCE OF DhcpPoolNextServerEntry
          MAX-ACCESS  not-accessible
          STATUS      current
          DESCRIPTION "dhcpPoolNextServerTable"
          ::= { dhcpServer 10 }
          
--xxx.100.13.2.10.1
dhcpPoolNextServerEntry OBJECT-TYPE
          SYNTAX      DhcpPoolNextServerEntry
          MAX-ACCESS  not-accessible
          STATUS      current
          DESCRIPTION "dhcpPoolNextServerEntry"
          INDEX { dhcpPoolNextServerPoolName }
          ::= { dhcpPoolNextServerTable  1 }

DhcpPoolNextServerEntry ::= SEQUENCE
{
     dhcpPoolNextServerPoolName  	DisplayString,
     dhcpPoolNextServerIpAddress1 	IpAddress,
     dhcpPoolNextServerIpAddress2  	IpAddress,
     dhcpPoolNextServerIpAddress3	IpAddress,
     dhcpPoolNextServerIpAddress4	IpAddress,
     dhcpPoolNextServerIpAddress5	IpAddress,
     dhcpPoolNextServerIpAddress6	IpAddress,
     dhcpPoolNextServerIpAddress7	IpAddress,
     dhcpPoolNextServerIpAddress8	IpAddress,
     dhcpPoolNextServerStatus	INTEGER
}

--xxx.100.13.2.10.1
dhcpPoolNextServerPoolName OBJECT-TYPE
          SYNTAX      DisplayString
          MAX-ACCESS  not-accessible
          STATUS      current
          DESCRIPTION "PoolName, simply specify a string which 
                      string size NO MORE THAN 8"
          ::= { dhcpPoolNextServerEntry 1 } 
          
--xxx.100.13.2.10.2
dhcpPoolNextServerIpAddress1 OBJECT-TYPE
          SYNTAX      IpAddress
          MAX-ACCESS  read-create
          STATUS      current
          DESCRIPTION "IP address,must"
          ::= { dhcpPoolNextServerEntry 2 }          
          
--xxx.100.13.2.10.3
dhcpPoolNextServerIpAddress2 OBJECT-TYPE
          SYNTAX      IpAddress
          MAX-ACCESS  read-create
          STATUS      current
          DESCRIPTION "IP address,option"
          ::= { dhcpPoolNextServerEntry 3 }          
          
--xxx.100.13.2.10.4
dhcpPoolNextServerIpAddress3 OBJECT-TYPE
          SYNTAX      IpAddress
          MAX-ACCESS  read-create
          STATUS      current
          DESCRIPTION "IP address,option"
          ::= { dhcpPoolNextServerEntry 4 }          
          
--xxx.100.13.2.10.5
dhcpPoolNextServerIpAddress4 OBJECT-TYPE
          SYNTAX      IpAddress
          MAX-ACCESS  read-create
          STATUS      current
          DESCRIPTION "IP address,option"
          ::= { dhcpPoolNextServerEntry 5 }          
          
--xxx.100.13.2.10.6
dhcpPoolNextServerIpAddress5 OBJECT-TYPE
          SYNTAX      IpAddress
          MAX-ACCESS  read-create
          STATUS      current
          DESCRIPTION "IP address,option"
          ::= { dhcpPoolNextServerEntry 6 }          
          
--xxx.100.13.2.10.7
dhcpPoolNextServerIpAddress6 OBJECT-TYPE
          SYNTAX      IpAddress
          MAX-ACCESS  read-create
          STATUS      current
          DESCRIPTION "IP address,option"
          ::= { dhcpPoolNextServerEntry 7 }          
          
--xxx.100.13.2.10.8
dhcpPoolNextServerIpAddress7 OBJECT-TYPE
          SYNTAX      IpAddress
          MAX-ACCESS  read-create
          STATUS      current
          DESCRIPTION "IP address,option"
          ::= { dhcpPoolNextServerEntry 8 }          

--xxx.100.13.2.10.9
dhcpPoolNextServerIpAddress8 OBJECT-TYPE
          SYNTAX      IpAddress
          MAX-ACCESS  read-create
          STATUS      current
          DESCRIPTION "IP address,option"
          ::= { dhcpPoolNextServerEntry 9 }  

--xxx.100.13.2.10.10
dhcpPoolNextServerStatus OBJECT-TYPE
          SYNTAX    INTEGER
            	    {
            	    	createAndGo(0),
               		active(1),
               		destroy(2)
            	    } 
          MAX-ACCESS  read-create
          STATUS      current
          DESCRIPTION "status machine"
          ::= { dhcpPoolNextServerEntry 10 }            
          
--********************************************************************************************************

--xxx.100.13.2.11
dhcpPoolWinsTable OBJECT-TYPE
          SYNTAX      SEQUENCE OF DhcpPoolWinsEntry
          MAX-ACCESS  not-accessible
          STATUS      current
          DESCRIPTION "dhcpPoolWinsTable"
          ::= { dhcpServer 11 }
          
--xxx.100.13.2.11.1
dhcpPoolWinsEntry OBJECT-TYPE
          SYNTAX      DhcpPoolWinsEntry
          MAX-ACCESS  not-accessible
          STATUS      current
          DESCRIPTION "configure Wins sever address"
          INDEX { dhcpPoolDnsSerPoolName }
          ::= { dhcpPoolWinsTable 1 }

DhcpPoolWinsEntry ::= SEQUENCE
{
     dhcpPoolWinsPoolName  	DisplayString,
     dhcpPoolWinsIpAddress1 	IpAddress,
     dhcpPoolWinsIpAddress2  	IpAddress,
     dhcpPoolWinsIpAddress3	IpAddress,
     dhcpPoolWinsIpAddress4	IpAddress,
     dhcpPoolWinsIpAddress5	IpAddress,
     dhcpPoolWinsIpAddress6	IpAddress,
     dhcpPoolWinsIpAddress7	IpAddress,
     dhcpPoolWinsIpAddress8	IpAddress,
     dhcpPoolWinsStatus		INTEGER
}

--xxx.100.13.2.11.1
dhcpPoolWinsPoolName OBJECT-TYPE
          SYNTAX      DisplayString
          MAX-ACCESS  not-accessible
          STATUS      current
          DESCRIPTION "PoolName, simply specify a string which 
                      string size NO MORE THAN 8"
          ::= { dhcpPoolWinsEntry 1 } 
          
--xxx.100.13.2.11.2
dhcpPoolWinsIpAddress1 OBJECT-TYPE
          SYNTAX      IpAddress
          MAX-ACCESS  read-create
          STATUS      current
          DESCRIPTION "IP address,must"
          ::= { dhcpPoolWinsEntry 2 }          
          
--xxx.100.13.2.11.3
dhcpPoolWinsIpAddress2 OBJECT-TYPE
          SYNTAX      IpAddress
          MAX-ACCESS  read-create
          STATUS      current
          DESCRIPTION "IP address,option"
          ::= { dhcpPoolWinsEntry 3 }          
          
--xxx.100.13.2.11.4
dhcpPoolWinsIpAddress3 OBJECT-TYPE
          SYNTAX      IpAddress
          MAX-ACCESS  read-create
          STATUS      current
          DESCRIPTION "IPaddress,option"
          ::= { dhcpPoolWinsEntry 4 }          
          
--xxx.100.13.2.11.5
dhcpPoolWinsIpAddress4 OBJECT-TYPE
          SYNTAX      IpAddress
          MAX-ACCESS  read-create
          STATUS      current
          DESCRIPTION "IP address,option"
          ::= { dhcpPoolWinsEntry 5 }          
          
--xxx.100.13.2.11.6
dhcpPoolWinsIpAddress5 OBJECT-TYPE
          SYNTAX      IpAddress
          MAX-ACCESS  read-create
          STATUS      current
          DESCRIPTION "IP address,option"
          ::= { dhcpPoolWinsEntry 6 }          
          
--xxx.100.13.2.11.7
dhcpPoolWinsIpAddress6 OBJECT-TYPE
          SYNTAX      IpAddress
          MAX-ACCESS  read-create
          STATUS      current
          DESCRIPTION "IP address,option"
          ::= { dhcpPoolWinsEntry 7 }          
          
--xxx.100.13.2.11.8
dhcpPoolWinsIpAddress7 OBJECT-TYPE
          SYNTAX      IpAddress
          MAX-ACCESS  read-create
          STATUS      current
          DESCRIPTION "IP address,option"
          ::= { dhcpPoolWinsEntry 8 }          

--xxx.100.13.2.11.9
dhcpPoolWinsIpAddress8 OBJECT-TYPE
          SYNTAX      IpAddress
          MAX-ACCESS  read-create
          STATUS      current
          DESCRIPTION "IP address,option"
          ::= { dhcpPoolWinsEntry 9 }  

--xxx.100.13.2.11.10
dhcpPoolWinsStatus OBJECT-TYPE
          SYNTAX    INTEGER
            	    {
            	    	createAndGo(0),
               		active(1),
               		destroy(2)
            	    } 
          MAX-ACCESS  read-create
          STATUS      current
          DESCRIPTION "configure wins server status machine"
          ::= { dhcpPoolWinsEntry 10 }  
--********************************************************************************************************

--xxx.100.13.2.12
dhcpServerLeaseBindingTable OBJECT-TYPE
          SYNTAX      SEQUENCE OF DhcpServerLeaseBindingEntry
          MAX-ACCESS  not-accessible
          STATUS      current
          DESCRIPTION "express IP address and MAC address bind status"
          ::= { dhcpServer 12 }
          
--xxx.100.13.2.12.1
dhcpServerLeaseBindingEntry OBJECT-TYPE
          SYNTAX      DhcpServerLeaseBindingEntry
          MAX-ACCESS  not-accessible
          STATUS      current
          DESCRIPTION "express IP address and MAC address bind status"
          INDEX { dhcpServerLeaseBindingIp, dhcpServerLeaseBindingType }
          ::= { dhcpServerLeaseBindingTable 1 }

DhcpServerLeaseBindingEntry ::= SEQUENCE
{
     dhcpServerLeaseBindingIp  		IpAddress,
     dhcpServerLeaseBindingType		INTEGER,     
     dhcpServerLeaseBindingMac 		DisplayString,
     dhcpServerLeaseBindingLeaseTime  	INTEGER
}

--xxx.100.13.2.12.1.1
dhcpServerLeaseBindingIp  OBJECT-TYPE
          SYNTAX      IpAddress
          MAX-ACCESS  read-only
          STATUS      current
          DESCRIPTION "certain address appointed, format is x.x.x.x"
          ::= { dhcpServerLeaseBindingEntry 1 }  

 
--xxx.100.13.2.12.1.2
dhcpServerLeaseBindingType  OBJECT-TYPE
          SYNTAX      INTEGER
          	      {
          	      	manual(1),
          	      	dynamic(2)
          	      }
          MAX-ACCESS  read-only
          STATUS      current
          DESCRIPTION "manual express handcraft bind style;dynamic express dynamic distribution style"
          ::= { dhcpServerLeaseBindingEntry 2 }  
  
--xxx.100.13.2.12.1.3
dhcpServerLeaseBindingMac  OBJECT-TYPE
          SYNTAX      DisplayString
          MAX-ACCESS  read-only
          STATUS      current
          DESCRIPTION "MAC address"
          ::= { dhcpServerLeaseBindingEntry 3 }    
  
--xxx.100.13.2.12.1.4
dhcpServerLeaseBindingLeaseTime  OBJECT-TYPE
          SYNTAX      INTEGER
          MAX-ACCESS  read-only
          STATUS      current
          DESCRIPTION "rent term"
          ::= { dhcpServerLeaseBindingEntry 4 }     
--******************************************************************************************************** 
--******************************************************************************************************** 
--xxx.100.13.3 
    dhcpSnooping                     OBJECT IDENTIFIER ::= { pridhcp 3 }

--xxx.100.13.3.1
        dhcpSnoopingEnable OBJECT-TYPE
            SYNTAX  INTEGER
            	{
               		noEnable(0),
               		enable(1)              		           	
            	}
            MAX-ACCESS  read-create
            STATUS  current
            DESCRIPTION "Enable the dhcp snooping function."
            ::= { dhcpSnooping 1 } 

--xxx.100.13.3.2
        dhcpSnoopingBindingEnalbe OBJECT-TYPE
            SYNTAX  INTEGER
            	{
               		noEnable(0),
               		enable(1)              		           	
            	}
            MAX-ACCESS  read-create
            STATUS  current
            DESCRIPTION "Enable the dhcp snooping binding function."
            ::= { dhcpSnooping 2 }
			
--xxx.100.13.3.3
        dhcpSnoopingVlanEnable OBJECT-TYPE
          SYNTAX      OCTET STRING
          MAX-ACCESS  read-create
          STATUS      current
          DESCRIPTION " Enable the dhcp snooping on vlan list string, the vlan list string is input 
						like as '1-2'. If the next time input the string '3-5',then the final vlan list
						is '1-5'.If input the string 'NULL',then delete the whole vlan list."
            ::= { dhcpSnooping 3 }	

--xxx.100.13.3.4
        dhcpSnoopingInformationEnalbe OBJECT-TYPE
            SYNTAX  INTEGER
            	{
               		noEnable(0),
               		enable(1)              		           	
            	}
            MAX-ACCESS  read-create
            STATUS  current
            DESCRIPTION "Enable the dhcp snooping information function."
            ::= { dhcpSnooping 4 }	
			
--xxx.100.13.3.5			
		dhcpSnoopingLimitRate   OBJECT-TYPE
            SYNTAX      INTEGER(0..100) 
            MAX-ACCESS  read-create
            STATUS      current
            DESCRIPTION "Configration of dhcp packets rate on the switch, the default rate of dhcp packets received is 100 pps."
            ::= { dhcpSnooping 5}     	

--xxx.100.13.3.6			
		dhcpSnoopingActionMaxNum   OBJECT-TYPE
            SYNTAX      INTEGER(0..200) 
            MAX-ACCESS  read-create
            STATUS      current
            DESCRIPTION "Configration of the maximum number of dhcp snooping action on a port, the default value is 10."
            ::= { dhcpSnooping 6}  			

--xxx.100.13.3.7			
		dhcpSnoopingbindingARP   OBJECT-TYPE
			SYNTAX  INTEGER
            	{
               		notBindingARP(0),
               		bindingARP(1)              		           	
            	}
            MAX-ACCESS  read-create
            STATUS      current
            DESCRIPTION "If set(0), the static ARP entry is not added when the dhcp snooping is created,
			            if set(1), the static ARP entry is added according to the dhcp snooping binding,
			            the priority of this static ARP entry is lower than that configured by administrator."
            ::= { dhcpSnooping 7}  	

--xxx.100.13.3.8
        dhcpSnoopingInformationOptionDelimiter  OBJECT-TYPE
            SYNTAX  INTEGER
            	{
               		colon(0),
               		dot(1),
					slash(2),
					space(3)		
            	}
            MAX-ACCESS  read-create
            STATUS  current
            DESCRIPTION "If set(0), then use colon to compart sub-option parameters,
			              set(1), use dot to compart sub-option parameters,
						  set(2), use slash to compart sub-option parameters,
						  set(3), use space to compart sub-option parameters
						  the default value is set(2)."
            ::= { dhcpSnooping 8 }	

--xxx.100.13.3.9
        dhcpSnoopingInformationOptionSubscriberIDFormat OBJECT-TYPE
            SYNTAX  INTEGER
            	{
               		hex(0),
               		acsii(1),
					vs-hp(2)	
            	}
            MAX-ACCESS  read-create
            STATUS  current
            DESCRIPTION "If set(0), then use hex format of vlan and mac address,
			              set(1), use ACSII format of vlan and mac address,
						  set(2), use vs-hp format to keep compatibility with HP,
						  the default value is set(1)."
            ::= { dhcpSnooping 9 }

--xxx.100.13.3.10
        dhcpSnoopingInformationOptionRemoteID OBJECT-TYPE
        SYNTAX      DisplayString(SIZE(1..64))
            MAX-ACCESS  read-create
            STATUS  current
            DESCRIPTION "If input the 'standard' string ,then use vlan mac address format for option82 sub-option 2, 
			             other string, that be used as romote ID of option82 sub-option 2,
						 the default string is 'standard'."
            ::= { dhcpSnooping 10 } 
					
--xxx.100.13.3.11			
		dhcpSnoopingInformationOptionAllowUntrusted   OBJECT-TYPE
			SYNTAX  INTEGER
            	{
               		notAllowUntrusted(0),
               		allowUntrusted(1)              		           	
            	}
            MAX-ACCESS  read-create
            STATUS      current
            DESCRIPTION "If set(0), the dhcp packets with option82 are discarded, 
						if set (1), the dhcp packets with option82 are permitted, and the content of option82 is not changed."
            ::= { dhcpSnooping 11 }  

--xxx.100.13.3.12
        dhcpSnoopingOptionSelfDefinedSubscriberIDFormat   OBJECT-TYPE
            SYNTAX  INTEGER
            	{
               		hex(0),
					ascii(1)
            	}
            MAX-ACCESS  read-create
            STATUS  current
            DESCRIPTION "If set(0), then use ASCII format to generate sub-scriber ID,
			              set(1), use hex format to generate sub-scriber ID,
						  the default value is set(1)."
            ::= { dhcpSnooping 12 }				

--xxx.100.13.3.13
        dhcpSnoopingOptionSelfDefinedRemoteIDFormat   OBJECT-TYPE
            SYNTAX  INTEGER
            	{
					hex(0),
					ascii(1)
            	}
            MAX-ACCESS  read-create
            STATUS  current
            DESCRIPTION "If set(0), then use ASCII format to generate remote ID,
			              set(1), use hex format to generate remote ID,
						  the default value is set(1)."
            ::= { dhcpSnooping 13 }	

--xxx.100.13.3.14
		dhcpSnoopingOptionSelfDefinedSubscriberID   OBJECT-TYPE
            SYNTAX  DisplayString(SIZE(1..128))
            MAX-ACCESS  read-create
            STATUS  current
            DESCRIPTION "If user does not configure the circuit-id of option82 explicitly on a port, then 
			             the user can self define format to generate the circuit-id, the format options include
						 vlan, port, ID, self designed string, the subscriber ID may be only one or any combination of 
						 them,and is strictly generated according to the sequence of format options, the ID option 
						 includes switch ID and remote-mac, but the user just selects only one of them, also In the 
						 swtich ID, it includes mac and hostname options, the user just selects only one of two, the 
						 maximum length of self-designed striing is 64.
						 if user inputs the string 'NULL', then delete the last configuration.
						 For example, if select vlan ,ID(swtich-id(mac)), and string 'str' format,
						 the user can input the string like as 'vlan id swtich-id mac string str'."
            ::= { dhcpSnooping 14 }	
			
--xxx.100.13.3.15
        dhcpSnoopingOptionSelfDefinedRemoteID   OBJECT-TYPE
            SYNTAX  DisplayString(SIZE(1..64))
            MAX-ACCESS  read-create
            STATUS  current
            DESCRIPTION "If user does not configure the remote-id of option82 explicitly on a port, then 
			             the user can self define format to generate the remote-id, the format options include
						 mac,hostname and self designed string, the remote ID may be only one or any combination of 
						 them,and is strictly generated according to the sequence of format options, 
						 the maximum length of self designed striing is 32.
						 If user inputs the string 'NULL', then delete the last configuration.
						 For example, if select hostname,mac,and string 'str' format,
						 the user can input the string like as 'hostname mac string str'."
            ::= { dhcpSnooping 15 }

--xxx.100.13.3.16
        dhcpSnoopingClearBinding   OBJECT-TYPE
            SYNTAX  DisplayString(SIZE(1..64))
            MAX-ACCESS  read-create
            STATUS  current
            DESCRIPTION "Clear the dhcp snooping bindings, the user can specify the mac address and vlan ID,
						or interface name and vlan ID ,or vlan ID, if input 'all' string, then clear all of the 
						bindings,if input 'mac 00-24-e3-3a-f3-24 vlan 2', then clear the bindings with mac address 
						00-24-e3-3a-f3-24 in the vlan 2, if input 'interface ethernet0/0/1 vlan 2', then clear all of 
						the bidings on the interface ethernet0/0/1 in the vlan 2, if input 'vlan 1' string ,then clear 
						all of bindings in the vlan 1."
            ::= { dhcpSnooping 16 }
--************************************************************************			
--dhcp snooping sub table
--************************************************************************
--dhcpSnoopingPortConfigTable
--xxx.100.13.3.17
		dhcpSnoopingPortConfigTable OBJECT-TYPE
          SYNTAX      SEQUENCE OF DhcpSnoopingPortConfigEntry
          MAX-ACCESS  not-accessible
          STATUS      current
          DESCRIPTION "After enable the dhcp snooping function, the administrator can configure the port information."
          ::= { dhcpSnooping 17 }
          	   
--xxx.100.13.3.17.1
dhcpSnoopingPortConfigEntry OBJECT-TYPE
          SYNTAX      DhcpSnoopingPortConfigEntry
          MAX-ACCESS  not-accessible
          STATUS      current
          DESCRIPTION "A conceptual row of dhcpSnoopingPortConfigTable."
          INDEX { dhcpSnoopingPortIndex } 
          ::= { dhcpSnoopingPortConfigTable 1 }
          
DhcpSnoopingPortConfigEntry ::= SEQUENCE
{
    dhcpSnoopingPortIndex	        INTEGER,
	dhcpSnoopingUserControlMaxNum	INTEGER,
	dhcpSnoopingUserControl		INTEGER,
	dhcpSnoopingTrust	        OCTET STRING,
	dhcpSnoopingBindingDot1x 	INTEGER,
	dhcpSnoopingSubScriberID	DisplayString,
	dhcpSnoopingAlarmCount		INTEGER,
	dhcpSnoopingBindingCount	INTEGER
}

--xxx.100.13.3.17.1.1
dhcpSnoopingPortIndex OBJECT-TYPE
          SYNTAX      INTEGER
          MAX-ACCESS  not-accessible
          STATUS      current
          DESCRIPTION "Configure the dhcp snooping function on the specified port."
          ::= { dhcpSnoopingPortConfigEntry 1 }       

--xxx.100.13.3.17.1.2
dhcpSnoopingUserControlMaxNum OBJECT-TYPE
          SYNTAX      INTEGER(0..1024)
          MAX-ACCESS  read-create
          STATUS      current
          DESCRIPTION "Configure the maximum of the binding users on a port, the range of binding users number is 
		              0-1024,the default number is 1024."
          ::= { dhcpSnoopingPortConfigEntry 2 }  

--xxx.100.13.3.17.1.3
dhcpSnoopingUserControl OBJECT-TYPE
          SYNTAX      INTEGER
		  {
				notEnable(0),
				enable(1)
		  }
          MAX-ACCESS  read-create
          STATUS      current
          DESCRIPTION "If set(0), not enable the user control function on a specified port,
		               if set(1), enable the user control function on a specified port,
					   the default value is set(0)."
          ::= { dhcpSnoopingPortConfigEntry 3 } 

--xxx.100.13.3.17.1.4
dhcpSnoopingTrust OBJECT-TYPE
          SYNTAX      OCTET STRING
          MAX-ACCESS  read-create
          STATUS      current
          DESCRIPTION "Configure trust function on a port or vlan list string.If input the string 'all', then trust 
		              all the vlan. If input the string '1-2', then only trust the DHCP packets with that 
					  vlan ID is 1 or 2. If input string 'NULL', then close the trust function on the port."
          ::= { dhcpSnoopingPortConfigEntry 4 }

--xxx.100.13.3.17.1.5
dhcpSnoopingBindingDot1x OBJECT-TYPE
          SYNTAX      INTEGER
		  {
				notEnable(0),
				enable(1)
		  }
          MAX-ACCESS  read-create
          STATUS      current
          DESCRIPTION "If set(0), not enable to notify dhcp snooping binding information to Dot1x module,
		               if set(1), enable to notify dhcp snooping binding information to Dot1x module,
					   the default value is set(0)."
          ::= { dhcpSnoopingPortConfigEntry 5 } 
		  
--xxx.100.13.3.17.1.6
dhcpSnoopingSubScriberID OBJECT-TYPE
        SYNTAX      DisplayString(SIZE(1..32))
            MAX-ACCESS  read-create
            STATUS  current
            DESCRIPTION "If input the 'standard' string ,then use vlan mac address format for option82 sub-option 2, 
			             other string, that be used as romote ID of option82 sub-option 2,
						 the default string is 'standard'."
            ::= { dhcpSnoopingPortConfigEntry 6 }
			
--xxx.100.13.3.17.1.7
dhcpSnoopingAlarmCount OBJECT-TYPE
            SYNTAX  INTEGER
            MAX-ACCESS  read-only
            STATUS  current
            DESCRIPTION "Show the alarm count of dhcp snooping on a specified port."
            ::= { dhcpSnoopingPortConfigEntry  7}		  
			
--xxx.100.13.3.17.1.8
dhcpSnoopingBindingCount OBJECT-TYPE
            SYNTAX  INTEGER
            MAX-ACCESS  read-only
            STATUS  current
            DESCRIPTION "Show the binding count of dhcp snooping on a specified port."
            ::= { dhcpSnoopingPortConfigEntry  8}	
			
--********************************************************************
--xxx.100.13.3.18
		dhcpSnoopingPortActionTable OBJECT-TYPE
          SYNTAX      SEQUENCE OF DhcpSnoopingPortActionEntry
          MAX-ACCESS  not-accessible
          STATUS      current
          DESCRIPTION "After enable the dhcp snooping function, the administrator can configure the port action."
          ::= { dhcpSnooping 18 }
          	   
--xxx.100.13.3.18.1
dhcpSnoopingPortActionEntry OBJECT-TYPE
          SYNTAX      DhcpSnoopingPortActionEntry
          MAX-ACCESS  not-accessible
          STATUS      current
          DESCRIPTION "A conceptual row of dhcpSnoopingPortActionTable."
          INDEX { dhcpSnoopingPortIndex } 
          ::= { dhcpSnoopingPortActionTable 1 }
          
DhcpSnoopingPortActionEntry ::= SEQUENCE
{
    dhcpSnoopingPort	INTEGER,
	dhcpSnoopingActionType	INTEGER,
	dhcpSnoopingActionRecoveryTime		INTEGER,
	dhcpSnoopingActionStatus	INTEGER
}
--xxx.100.13.3.18.1.1
dhcpSnoopingPort OBJECT-TYPE
          SYNTAX      INTEGER
          MAX-ACCESS  not-accessible
          STATUS      current
          DESCRIPTION "Configure the dhcp snooping function on the specified port."
          ::= { dhcpSnoopingPortActionEntry 1 }   
		  
--xxx.100.13.3.18.1.2
dhcpSnoopingActionType OBJECT-TYPE
            SYNTAX  INTEGER
            	{
               		noAction(0),
					shutdown(1),
					blackhole(2)
            	}
            MAX-ACCESS  read-create
            STATUS  current
            DESCRIPTION "If set(0), not to add any action, 
						 if set(1), add shutdown action ,
						 and if set(2), add blackhole action on  a port when detectd the DHCP server protended ."
            ::= { dhcpSnoopingPortActionEntry 2 }

--xxx.100.13.3.18.1.3
dhcpSnoopingActionRecoveryTime OBJECT-TYPE
            SYNTAX  INTEGER(10..3600)
            MAX-ACCESS  read-create
            STATUS  current
            DESCRIPTION "Configure the recovery time of action, the range time is 10-3600 seconds,
						the default value is 30 seconds."
            ::= { dhcpSnoopingPortActionEntry 3 }
            
--xxx.100.13.3.18.1.4
dhcpSnoopingActionStatus OBJECT-TYPE
            SYNTAX  INTEGER
            	{
               		destroy(0),
					active(1)
            	}
            MAX-ACCESS  read-create
            STATUS  current
            DESCRIPTION "If set(0), then destory an aciton configured previously,
						 if set(1), then configure an action on a port."
            ::= { dhcpSnoopingPortActionEntry 4 } 
		
--********************************************************************		
--dhcpSnoopingStaticBindingTable
--xxx.100.13.3.19
dhcpSnoopingStaticBindingTable OBJECT-TYPE
          SYNTAX      SEQUENCE OF DhcpSnoopingStaticBindingEntry
          MAX-ACCESS  not-accessible
          STATUS      current
          DESCRIPTION "After enable the dhcp snooping function, the administrator can configure or delete the dhcp 
		               snooping static binding."
          ::= { dhcpSnooping 19 }
          	   
--xxx.100.13.3.19.1
dhcpSnoopingStaticBindingEntry OBJECT-TYPE
          SYNTAX      DhcpSnoopingStaticBindingEntry
          MAX-ACCESS  not-accessible
          STATUS      current
          DESCRIPTION "A conceptual row of dhcpSnoopingStaticBindingTable."
          INDEX { dhcpSnoopingStaticBindingIP } 
          ::= { dhcpSnoopingStaticBindingTable 1 }
          
DhcpSnoopingStaticBindingEntry ::= SEQUENCE
{
     dhcpSnoopingStaticBindingMAC  OCTET STRING,
     dhcpSnoopingStaticBindingIP   IpAddress,
	 dhcpSnoopingStaticBindingMAC  OCTET STRING,
     dhcpSnoopingStaticBindingMask   IpAddress,	 
     dhcpSnoopingStaticBindingPort   INTEGER, 
     dhcpSnoopingStaticBindingVid   INTEGER,
     dhcpSnoopingStaticBindingStatus	INTEGER
}

--xxx.100.13.3.19.1.1
dhcpSnoopingStaticBindingIP OBJECT-TYPE
          SYNTAX      IpAddress
          MAX-ACCESS  not-accessible
          STATUS      current
          DESCRIPTION "The one IP address just only identifies one ack binding entry."
          ::= { dhcpSnoopingStaticBindingEntry 1 } 

--xxx.100.13.3.19.1.2
dhcpSnoopingStaticBindingMAC OBJECT-TYPE
          SYNTAX      OCTET STRING(SIZE(17))
          MAX-ACCESS  read-create
          STATUS      current
          DESCRIPTION "Configure the MAC address of the static binding."
          ::= { dhcpSnoopingStaticBindingEntry 2 }       
 
--xxx.100.13.3.19.1.3
dhcpSnoopingStaticBindingMask OBJECT-TYPE
          SYNTAX      IpAddress
          MAX-ACCESS  read-create
          STATUS      current
          DESCRIPTION "Configure the IP address mask of the static binding."
          ::= { dhcpSnoopingStaticBindingEntry 3 }
		  
--xxx.100.13.3.19.1.4
dhcpSnoopingStaticBindingPort OBJECT-TYPE
          SYNTAX      INTEGER
          MAX-ACCESS  read-create
          STATUS      current
          DESCRIPTION "Configure the port of the static binding."
          ::= { dhcpSnoopingStaticBindingEntry 4 }

--xxx.100.13.3.19.1.5
dhcpSnoopingStaticBindingVid OBJECT-TYPE
          SYNTAX      INTEGER
          MAX-ACCESS  read-create
          STATUS      current
          DESCRIPTION "Configure the vlan ID of the static binding."
          ::= { dhcpSnoopingStaticBindingEntry 5 }
		  
--xxx.100.13.3.19.1.6
dhcpSnoopingStaticBindingStatus OBJECT-TYPE
          SYNTAX      INTEGER
		  {
			destory(0),
			active(1)
		  }
          MAX-ACCESS  read-create
          STATUS      current
          DESCRIPTION "If set(0), then distory a specified static binding that has been configured,
		               if set(1), create a specified static binding according to the input content."
          ::= { dhcpSnoopingStaticBindingEntry 6 }  		  
--****************************************************************			
--dhcpSnoopingAckBindingInfoTable			
--****************************************************************
--xxx.100.13.3.20
dhcpSnoopingAckBindingInfoTable OBJECT-TYPE
          SYNTAX      SEQUENCE OF DhcpSnoopingAckBindingInfoEntry
          MAX-ACCESS  not-accessible
          STATUS      current
          DESCRIPTION "Show the specified bindings after received the DHCP ACK packets."
          ::= { dhcpSnooping 20 }
          	   
--xxx.100.13.3.20.1
dhcpSnoopingAckBindingInfoEntry OBJECT-TYPE
          SYNTAX      DhcpSnoopingAckBindingInfoEntry
          MAX-ACCESS  not-accessible
          STATUS      current
          DESCRIPTION "A conceptual row of dhcpSnoopingAckBindingInfoTable."
          INDEX { dhcpSnoopingAckBindingIP } 
          ::= { dhcpSnoopingAckBindingInfoTable 1 }
          
DhcpSnoopingAckBindingInfoEntry ::= SEQUENCE
{
     dhcpSnoopingAckBindingIP   IpAddress,
	 dhcpSnoopingAckBindingMAC  OCTET STRING,
	 dhcpSnoopingAckBindingPort   INTEGER,	
	 dhcpSnoopingAckBindingVid   INTEGER,
	 dhcpSnoopingAckBindingLease  Counter32,
	 dhcpSnoopingAckBindingFlag  DisplayString
}

--xxx.100.13.3.20.1.1
dhcpSnoopingAckBindingIP OBJECT-TYPE
          SYNTAX      IpAddress
          MAX-ACCESS  not-accessible
          STATUS      current
          DESCRIPTION "The one IP address just only identifies one ack binding entry."
          ::= { dhcpSnoopingAckBindingInfoEntry 1 } 
		  
--xxx.100.13.3.20.1.2
dhcpSnoopingAckBindingMAC OBJECT-TYPE
          SYNTAX      OCTET STRING(SIZE(17))
          MAX-ACCESS  read-only
          STATUS      current
          DESCRIPTION "Show the MAC address of the ack binding."
          ::= { dhcpSnoopingAckBindingInfoEntry 2 }       
 
--xxx.100.13.3.20.1.3
dhcpSnoopingAckBindingPort OBJECT-TYPE
          SYNTAX      INTEGER
          MAX-ACCESS  read-only
          STATUS      current
          DESCRIPTION "Show the port index information of the ack binding."
          ::= { dhcpSnoopingAckBindingInfoEntry 3 } 

--xxx.100.13.3.20.1.4
dhcpSnoopingAckBindingVid OBJECT-TYPE
          SYNTAX      INTEGER
          MAX-ACCESS  read-only
          STATUS      current
          DESCRIPTION "Show the Vid information of the ack bidning."
          ::= { dhcpSnoopingAckBindingInfoEntry 4 }

--xxx.100.13.3.20.1.5
dhcpSnoopingAckBindingLease OBJECT-TYPE
          SYNTAX      Counter32
          MAX-ACCESS  read-only
          STATUS      current
          DESCRIPTION "Show the lease of the ack binding. The lease of static binding is infinite, the lease of dynamic binding comes from the DHCP 
		               reply packets of dhcp server."
          ::= { dhcpSnoopingAckBindingInfoEntry 5 }

--xxx.100.13.3.20.1.6
dhcpSnoopingAckBindingFlag OBJECT-TYPE
          SYNTAX      DisplayString(SIZE(1..10))
          MAX-ACCESS  read-only
          STATUS      current
          DESCRIPTION "Show the type of the ack binding. The flag 'S' indentifies the static type binding, 'D' indentifies the dynamic type binding,
                       'U' indentifies that bindings are uploaded from the server, 'O' indentifies that DHCP request packet is 
					   with option82 information, 'X' indentifies that the bindings have been notified Dot1x module, and the 
                       client is control under the Dot1x function, 'L' indentifies that the binding entry has been sent to the driver,
                       'E' indentifies that the notification to Dot1x module is failed."
          ::= { dhcpSnoopingAckBindingInfoEntry 6 }		  		  
--************************************************************
--dhcpSnoopingRequestBindingInfoTable			
--xxx.100.13.3.21
dhcpSnoopingRequestBindingInfoTable OBJECT-TYPE
          SYNTAX      SEQUENCE OF DhcpSnoopingRequestBindingInfoEntry
          MAX-ACCESS  not-accessible
          STATUS      current
          DESCRIPTION "Show the specified bindings after received the DHCP request packets."
          ::= { dhcpSnooping 21 }
          	   
--xxx.100.13.3.21.1
dhcpSnoopingRequestBindingInfoEntry OBJECT-TYPE
          SYNTAX      DhcpSnoopingRequestBindingInfoEntry
          MAX-ACCESS  not-accessible
          STATUS      current
          DESCRIPTION "A conceptual row of dhcpSnoopingRequestBindingInfoTable."
          INDEX { dhcpSnoopingRequestBindingIP } 
          ::= { dhcpSnoopingRequestBindingInfoTable 1 }
          
DhcpSnoopingRequestBindingInfoEntry ::= SEQUENCE
{
         dhcpSnoopingRequestBindingIP   IpAddress,
	 dhcpSnoopingRequestBindingMAC  OCTET STRING,
	 dhcpSnoopingRequestBindingPort   INTEGER,	
	 dhcpSnoopingRequestBindingVid   INTEGER,
	 dhcpSnoopingRequestBindingLease  Counter32
}

--xxx.100.13.3.21.1.1
dhcpSnoopingRequestBindingIP OBJECT-TYPE
          SYNTAX      IpAddress
          MAX-ACCESS  not-accessible
          STATUS      current
          DESCRIPTION "The one IP address just only identifies one Request binding entry."
          ::= { dhcpSnoopingRequestBindingInfoEntry 1 }
		  
--xxx.100.13.3.21.1.2
dhcpSnoopingRequestBindingMAC OBJECT-TYPE
          SYNTAX      OCTET STRING(SIZE(17))
          MAX-ACCESS  read-only
          STATUS      current
          DESCRIPTION "Show the MAC address of the Request binding."
          ::= { dhcpSnoopingRequestBindingInfoEntry 2 }       
  
--xxx.100.13.3.21.1.3
dhcpSnoopingRequestBindingPort OBJECT-TYPE
          SYNTAX      INTEGER
          MAX-ACCESS  read-only
          STATUS      current
          DESCRIPTION "Show the port index information of the Request binding."
          ::= { dhcpSnoopingRequestBindingInfoEntry 3 } 

--xxx.100.13.3.21.1.4
dhcpSnoopingRequestBindingVid OBJECT-TYPE
          SYNTAX      INTEGER
          MAX-ACCESS  read-only
          STATUS      current
          DESCRIPTION "Show the Vid information of the Request binding."
          ::= { dhcpSnoopingRequestBindingInfoEntry 4 }
		  
--xxx.100.13.3.21.1.5
dhcpSnoopingRequestBindingLease OBJECT-TYPE
          SYNTAX      Counter32
          MAX-ACCESS  read-only
          STATUS      current
          DESCRIPTION "Show the lease of the Request binding."
          ::= { dhcpSnoopingRequestBindingInfoEntry 5 }		
--*******************************************************************
--dhcpSnoopingAlarmInfoTable			
--*******************************************************************
--xxx.100.13.3.22
dhcpSnoopingAlarmInfoTable OBJECT-TYPE
          SYNTAX      SEQUENCE OF DhcpSnoopingAlarmInfoEntry
          MAX-ACCESS  not-accessible
          STATUS      current
          DESCRIPTION "Show the dhcp snooping alarm information."
          ::= { dhcpSnooping 22 }
                 
--xxx.100.13.3.22.1
dhcpSnoopingAlarmInfoEntry OBJECT-TYPE
          SYNTAX      DhcpSnoopingAlarmInfoEntry
          MAX-ACCESS  not-accessible
          STATUS      current
          DESCRIPTION "A conceptual row of dhcpSnoopingAlarmInfoTable."
          INDEX { dhcpSnoopingAlarmInfoPortIndex, dhcpSnoopingAlarmInfoNum} 
          ::= { dhcpSnoopingAlarmInfoTable 1 }
          
DhcpSnoopingAlarmInfoEntry ::= SEQUENCE
{
     dhcpSnoopingAlarmInfoPortIndex     INTEGER,
	 dhcpSnoopingAlarmInfoNum			INTEGER,
     dhcpSnoopingAlarmInfoType          INTEGER,
     dhcpSnoopingAlarmInfoBlackholeMAC  OCTET STRING,
     dhcpSnoopingAlarmInfoRecoveryTime  DisplayString,
     dhcpSnoopingAlarmInfoRecoveryActionStatus INTEGER
}

--xxx.100.13.3.22.1.1
dhcpSnoopingAlarmInfoPortIndex OBJECT-TYPE
          SYNTAX      INTEGER
          MAX-ACCESS  not-accessible
          STATUS      current
          DESCRIPTION "The port sequence of the alarm events."
          ::= { dhcpSnoopingAlarmInfoEntry 1 }  

--xxx.100.13.3.22.1.2
dhcpSnoopingAlarmInfoNum OBJECT-TYPE
          SYNTAX      INTEGER
          MAX-ACCESS  not-accessible
          STATUS      current
          DESCRIPTION "The sequence of the alarm events on a port."
          ::= { dhcpSnoopingAlarmInfoEntry 2 } 		  

--xxx.100.13.3.22.1.3
dhcpSnoopingAlarmInfoType OBJECT-TYPE
          SYNTAX      INTEGER
          MAX-ACCESS  read-only
          STATUS      current
          DESCRIPTION "Show the type information of the alarm event."
          ::= { dhcpSnoopingAlarmInfoEntry 3 }  

--xxx.100.13.3.22.1.4
dhcpSnoopingAlarmInfoBlackholeMAC OBJECT-TYPE
          SYNTAX      OCTET STRING
          MAX-ACCESS  read-only
          STATUS      current
          DESCRIPTION "Show the blackhole mac address of the alarm event."
          ::= { dhcpSnoopingAlarmInfoEntry 4 } 
          
--xxx.100.13.3.22.1.5
dhcpSnoopingAlarmInfoRecoveryTime OBJECT-TYPE
          SYNTAX      DisplayString
          MAX-ACCESS  read-only
          STATUS      current
          DESCRIPTION "Show the recovery time of the alarm event."
          ::= { dhcpSnoopingAlarmInfoEntry 5 }     
		  
--xxx.100.13.3.22.1.6
dhcpSnoopingAlarmInfoRecoveryActionStatus OBJECT-TYPE
          SYNTAX      INTEGER
          MAX-ACCESS  read-only
          STATUS      current
          DESCRIPTION "Show the status of the recovery  action."
          ::= { dhcpSnoopingAlarmInfoEntry 6 } 
--**********************************************************************
--dhcpSnoopingStatisticTable			
--**********************************************************************
--xxx.100.13.3.23 
    dhcpSnoopingStatisticTable                     OBJECT IDENTIFIER ::= { dhcpSnooping 23 }
--xxx.100.13.3.23.1.1
dhcpSnoopingStatisticAlarmNum OBJECT-TYPE
          SYNTAX      INTEGER
          MAX-ACCESS  read-only
          STATUS      current
          DESCRIPTION "Show the total number of the alarm events."
          ::= { dhcpSnoopingStatisticTable 1 }       

--xxx.100.13.3.23.1.2
dhcpSnoopingStatisticAckBindingNum OBJECT-TYPE
          SYNTAX      INTEGER
          MAX-ACCESS  read-only
          STATUS      current
          DESCRIPTION "Show the total number of the ack bindings."
          ::= { dhcpSnoopingStatisticTable 2 }
		  
--xxx.100.13.3.23.1.3
dhcpSnoopingStatisticRequestBindingNum OBJECT-TYPE
          SYNTAX      INTEGER
          MAX-ACCESS  read-only
          STATUS      current
          DESCRIPTION "Show the total number of the request bindings."
          ::= { dhcpSnoopingStatisticTable 3 }

--xxx.100.13.3.23.1.4
dhcpSnoopingStatisticDropPktsNum OBJECT-TYPE
          SYNTAX      INTEGER
          MAX-ACCESS  read-only
          STATUS      current
          DESCRIPTION "Show the total number of the drop packets."
          ::= { dhcpSnoopingStatisticTable 4 }

--xxx.100.13.3.23.1.5
dhcpSnoopingStatisticDiscardPktsNum OBJECT-TYPE
          SYNTAX      INTEGER
          MAX-ACCESS  read-only
          STATUS      current
          DESCRIPTION "Show the total number of the discarded packets."
          ::= { dhcpSnoopingStatisticTable 5 }	
                 
--******************************************************************************************************** 
--dhcpSnoopingBlockedInfoTable			
--*******************************************************************
--xxx.100.13.3.24
dhcpSnoopingBlockedInfoTable OBJECT-TYPE
          SYNTAX      SEQUENCE OF DhcpSnoopingBlockedInfoEntry
          MAX-ACCESS  not-accessible
          STATUS      current
          DESCRIPTION "Show the dhcp snooping blocked information."
          ::= { dhcpSnooping 24 }
                 
--xxx.100.13.3.24.1
dhcpSnoopingBlockedInfoEntry OBJECT-TYPE
          SYNTAX      DhcpSnoopingBlockedInfoEntry
          MAX-ACCESS  not-accessible
          STATUS      current
          DESCRIPTION "A conceptual row of dhcpSnoopingBlockedInfoTable."
          INDEX { dhcpSnoopingBlockedInfoPortIndex, dhcpSnoopingBlockedInfoRecordingTime} 
          ::= { dhcpSnoopingBlockedInfoTable 1 }
          
DhcpSnoopingBlockedInfoEntry ::= SEQUENCE
{
     dhcpSnoopingBlockedInfoPortIndex     INTEGER,
	   dhcpSnoopingBlockedInfoRecordingTime		INTEGER,
     dhcpSnoopingBlockedInfoShow          OCTET STRING
}

--xxx.100.13.3.24.1.1
dhcpSnoopingBlockedInfoPortIndex OBJECT-TYPE
          SYNTAX      INTEGER
          MAX-ACCESS  not-accessible
          STATUS      current
          DESCRIPTION "The port sequence of the blocked information."
          ::= { dhcpSnoopingBlockedInfoEntry 1 }  

--xxx.100.13.3.24.1.2
dhcpSnoopingBlockedInfoRecordingTime OBJECT-TYPE
          SYNTAX      INTEGER
          MAX-ACCESS  not-accessible
          STATUS      current
          DESCRIPTION "The recording time of one blocked info entry  on a port."
          ::= { dhcpSnoopingBlockedInfoEntry 2 } 		  

--xxx.100.13.3.24.1.3
dhcpSnoopingBlockedInfoShow OBJECT-TYPE
          SYNTAX      OCTET STRING
          MAX-ACCESS  read-only
          STATUS      current
          DESCRIPTION "Show the blocked information of one blocked info entry."
          ::= { dhcpSnoopingBlockedInfoEntry 3 }  
   	 
--******************************************************************************************************** 
--portGroupMgt
--xxx.100.14.1
	systemPriority OBJECT-TYPE
	    SYNTAX  INTEGER  (0..65535)        	
	    MAX-ACCESS  read-create
	    STATUS  current
	    DESCRIPTION
	        "Modify the system priority which is used by port group."
	    ::= { priportGroup  1 }
	    
--xxx.100.14.2
	portGroupTable  OBJECT-TYPE
    	    SYNTAX     SEQUENCE OF PortGroupEntry
            MAX-ACCESS not-accessible
    	    STATUS  current
            DESCRIPTION
        	"This table contains port group information associated 
        	with the local system known to this agent."
    	    ::= { priportGroup 2 }
    
--xxx.100.14.2.1
	portGroupEntry  OBJECT-TYPE
    	    SYNTAX     PortGroupEntry
    	    MAX-ACCESS not-accessible
    	    STATUS     current
    	    DESCRIPTION
        	"Configure the port group information."
    	   INDEX { portGroupIndex }
    	   ::= { portGroupTable 1 }
    
	PortGroupEntry ::= SEQUENCE {
	    portGroupIndex		INTEGER,
	    portGroupMemberCount        INTEGER,  
	    loadBalance                 INTEGER,
	    portGroupInfo    		DisplayString
	}

--xxx.100.14.2.1.1
	portGroupIndex  OBJECT-TYPE
	    SYNTAX     INTEGER
	    MAX-ACCESS not-accessible
	    STATUS     current
	    DESCRIPTION
	        "Port group number."
	    ::= { portGroupEntry 1 }

--xxx.100.14.2.1.2
	portGroupMemberCount  OBJECT-TYPE
	    SYNTAX     INTEGER
	    MAX-ACCESS read-only
	    STATUS     current
	    DESCRIPTION
	        "The number of port group member."
	    ::= { portGroupEntry 2 }

--xxx.100.14.2.1.3    
	loadBalance  OBJECT-TYPE
	    SYNTAX     INTEGER
	               {
	               	    dst-src-mac(1),
	               	    dst-src-ip(2),
	               	    src-mac(3),
	               	    dst-mac(4),
	               	    src-ip(5),
	               	    dst-ip(6),
	               	    dst-src-mac-ip(7),
                        enhance-profile(8),
						dst-src-mac-vlan(9),
						dst-src-ip-port(10),
						dst-src-mac-ip-port(13),
						dst-src-mac-vlan-normal(14),
						dst-src-ip-port-normal(15),
						dst-src-mac-ip-port-normal(16)
	               }
	    MAX-ACCESS read-create
	    STATUS     current
	    DESCRIPTION
	        "Load balancing method:
	        dst-src-mac(1):destination and source mac address;
	        dst-src-ip(2):destination and source ip address;
	        src-mac(3):source mac address;
	        dst-mac(4):destination mac address;
	        src-ip(5):source ip address;
	        dst-ip(6):destination ip address;
	        dst-src-mac-ip(7):destination and source mac address, ip address;
			enhance-profile(8):enhance-profile;
			dst-src-mac-vlan(9):destination and source mac address, vlan;
			dst-src-ip-port(10):destination and source ip address, port;
			dst-src-mac-ip-port(13):destination and source mac address, ip address, port;
			dst-src-mac-vlan-normal(14):destination and source mac address, vlan, normal;
			dst-src-ip-port-normal(15):destination and source ip address, port, normal;
			dst-src-mac-ip-port-normal(16):destination and source mac address, ip address, port, normal.
	        If there is no member in the port group, the value is -1.
	        If you set value to the load balance method that your switch is not unsupported, it will return error. 
	        Please see the handbook and make sure that the load balance method is supported by your switch."
	    ::= { portGroupEntry 3 } 
	    
--xxx.100.14.2.1.4    
	portGroupInfo  OBJECT-TYPE
	    SYNTAX     DisplayString
	    MAX-ACCESS read-only
	    STATUS     current
	    DESCRIPTION
	        "Port group brief information. Format is ID, Mode, Partner ID, Ports and Load-balance.
	        If there is no member in the port group, the value is empty."
	    ::= { portGroupEntry 4 } 
	    
--xxx.100.14.3
	portGroupPortListTable  OBJECT-TYPE
    	    SYNTAX     SEQUENCE OF PortGroupPortListEntry
            MAX-ACCESS not-accessible
    	    STATUS  current
            DESCRIPTION
        	"This table contains port group member information associated 
        	with the local system known to this agent."
    	    ::= { priportGroup 3 }
    
--xxx.100.14.3.1
	portGroupPortListEntry  OBJECT-TYPE
    	    SYNTAX     PortGroupPortListEntry
    	    MAX-ACCESS not-accessible
    	    STATUS     current
    	    DESCRIPTION
        	"Configure the port group member information."
    	   INDEX { portGroupIndex, portGroupMemberIndex}
    	   ::= { portGroupPortListTable 1 }
    
	PortGroupPortListEntry ::= SEQUENCE {
	    portGroupMemberIndex        INTEGER,  
	    portGroupMemberName         DisplayString,
	    portGroupMemberMode    	INTEGER,
	    portGroupMemberPriority     INTEGER,
	    portGroupMemberTimeout      INTEGER,	    
	    portGroupMemberStatus       INTEGER
	}

--xxx.100.14.3.1.1
	portGroupMemberIndex  OBJECT-TYPE
	    SYNTAX     INTEGER
	    MAX-ACCESS not-accessible
	    STATUS     current
	    DESCRIPTION
	        "Port group member index. Format is group number and port index of member."
	    ::= { portGroupPortListEntry 1 }

--xxx.100.14.3.1.2    
	portGroupMemberName  OBJECT-TYPE
	    SYNTAX     DisplayString
	    MAX-ACCESS read-only
	    STATUS     current
	    DESCRIPTION
	        "The name of port group member."
	    ::= { portGroupPortListEntry 2 } 
	    
--xxx.100.14.3.1.3    
	portGroupMemberMode  OBJECT-TYPE
	    SYNTAX     INTEGER
	    {
	    			on(1),
	    			active(2),
	    			passive(3)
	    }
	    MAX-ACCESS read-only
	    STATUS     current
	    DESCRIPTION
	        "The mode of port group member."
	    ::= { portGroupPortListEntry 3 } 
	    
--xxx.100.14.3.1.4    
	portGroupMemberPriority  OBJECT-TYPE
	    SYNTAX     INTEGER (0..65535)
	    MAX-ACCESS read-write
	    STATUS     current
	    DESCRIPTION
	        "The port priority of port group member. If the port group mode is on, the value is -1."
	    ::= { portGroupPortListEntry 4 }
	    
--xxx.100.14.3.1.5    
	portGroupMemberTimeout  OBJECT-TYPE
	    SYNTAX     INTEGER 
	               {
	               	    long(0),
	               	    short(1)	               	    
	               }	    
	    MAX-ACCESS read-only
	    STATUS     current
	    DESCRIPTION
	        "The timeout mode of port group member. If the port group mode is on, the value is -1."
	    ::= { portGroupPortListEntry 5 }	     
	    
--xxx.100.14.3.1.6    
	portGroupMemberStatus  OBJECT-TYPE
	    SYNTAX     INTEGER 
	               {
	               	    unselected(0),
	               	    selected(1),
	               	    standby(2)
	               }	    
	    MAX-ACCESS read-only
	    STATUS     current
	    DESCRIPTION
	        "The status of port group member. If the port group mode is on, the value is -1."
	    ::= { portGroupPortListEntry 6 }	    	    	    	    

--******************************************************************************************************** 
--snmpMgt
--xxx.100.15.1
	snmpSecurityIpStatus OBJECT-TYPE
	    SYNTAX  INTEGER  
	    	   {
			enable(1),
			disable(0)
	            }         	
	    MAX-ACCESS  read-create
	    STATUS  current
	    DESCRIPTION
	        "Enable or disable secure IP address check function on the NMS."
	    ::= { prisnmpMgt  1 }
	    
--xxx.100.15.2            
	snmpTrapHostStatus OBJECT-TYPE
	    SYNTAX  INTEGER  
	    	   {
			enable(1),
			disable(0)
	            }         	
	    MAX-ACCESS  read-create
	    STATUS  current
	    DESCRIPTION
	        "Enable the switch to send Trap message.
	         This command is used for SNMP v1/v2."
	    ::= { prisnmpMgt  2 }  
	    
--xxx.100.15.3            
	snmpRmonStatus OBJECT-TYPE
	    SYNTAX  INTEGER  
	    	   {
			enable(1),
			disable(0)
	            }         	
	    MAX-ACCESS  read-create
	    STATUS  current
	    DESCRIPTION
	        "Enable/disable RMON."
	    ::= { prisnmpMgt  3 } 
	    
--******************************************************************************************************** 
   	    
--xxx.100.15.4
securityIpTable  OBJECT-TYPE
    SYNTAX     SEQUENCE OF SecurityIpEntry
    MAX-ACCESS not-accessible
    STATUS     current
    DESCRIPTION
        "A list of snmp securityIp entries."
    ::= { prisnmpMgt 4 }
    
--xxx.100.15.4.1
securityIpEntry  OBJECT-TYPE
    SYNTAX     SecurityIpEntry
    MAX-ACCESS not-accessible
    STATUS     current
    DESCRIPTION
        "Configure the secure IP address which is 
          allowed to access the switch on the NMS;"
    INDEX { securityIpIndex }
    ::= { securityIpTable 1 }
    
--xxx.100.15.4.1.1
SecurityIpEntry ::= SEQUENCE {
    securityIpIndex		INTEGER,
    securityIpAddress           IpAddress,  
    securityIpStatus            INTEGER
}

--xxx.100.15.4.1.1.2
securityIpIndex  OBJECT-TYPE
    SYNTAX     INTEGER
    MAX-ACCESS not-accessible
    STATUS     current
    DESCRIPTION
        "Index."
    ::= { securityIpEntry 1 }

--xxx.100.15.4.1.1.2
securityIpAddress  OBJECT-TYPE
    SYNTAX     IpAddress
    MAX-ACCESS read-create
    STATUS     current
    DESCRIPTION
        "The address of security."
    ::= { securityIpEntry 2 }

--xxx.100.15.4.1.1.3    
securityIpStatus  OBJECT-TYPE
    SYNTAX     INTEGER
               {
               	    active(1),
               	    destroy(2)
               }
    MAX-ACCESS read-create
    STATUS     current
    DESCRIPTION
        "Writing this to active(1) creates an entry.
         Writing this to destroy(2) destroys an entry."
    ::= { securityIpEntry 3 } 
  
--******************************************************************************************************** 
  
    	    
--xxx.100.15.5
trapDestTable  OBJECT-TYPE
    SYNTAX     SEQUENCE OF TrapDestEntry
    MAX-ACCESS not-accessible
    STATUS     current
    DESCRIPTION
        "A list of trap destination entries."
    ::= { prisnmpMgt 5 }
    
--xxx.100.15.5.1
trapDestEntry  OBJECT-TYPE
    SYNTAX     TrapDestEntry
    MAX-ACCESS not-accessible
    STATUS     current
    DESCRIPTION
        "This entry includes a destination IP address to which to send
        traps for this community."
    INDEX { trapDestIndex }
    ::= { trapDestTable 1 }
    
--xxx.100.15.5.1.1
TrapDestEntry ::= SEQUENCE {
    trapDestIndex		INTEGER,
    trapDestAddress             IpAddress,
    trapDestVersion             INTEGER,     
    trapDestCommunity           DisplayString,  
    trapDestStatus              INTEGER
}

--xxx.100.15.5.1.1.2
trapDestIndex  OBJECT-TYPE
    SYNTAX     INTEGER
    MAX-ACCESS not-accessible
    STATUS     current
    DESCRIPTION
        "Index"
    ::= { trapDestEntry 1 }

--xxx.100.15.5.1.1.2
trapDestAddress  OBJECT-TYPE
    SYNTAX     IpAddress
    MAX-ACCESS read-create
    STATUS     current
    DESCRIPTION
        "The address to send traps."
    ::= { trapDestEntry 2 }
    
--xxx.100.15.5.1.1.3
trapDestVersion OBJECT-TYPE
    SYNTAX     INTEGER
               {
                   version1(0),
                   version2(1)
               }
    MAX-ACCESS read-create
    STATUS     current
    DESCRIPTION
        "This variables represent the version of the Trap we wish to send to trap Receiver.
         If the value is 0, mean we wish to send Version 1 trap. If the value is 1,
         mean we wish to send version 2 trap. "
    ::= { trapDestEntry 3}
    
--xxx.100.15.5.1.1.4
trapDestCommunity  OBJECT-TYPE
    SYNTAX     DisplayString(SIZE(1..255))
    MAX-ACCESS read-create
    STATUS     current
    DESCRIPTION
        "A community to which this destination address belongs."
    ::= { trapDestEntry 4 }

--xxx.100.15.5.1.1.5    
trapDestStatus  OBJECT-TYPE
    SYNTAX     INTEGER
               {
               	    active(1),
               	    destroy(2)
               }
    MAX-ACCESS read-create
    STATUS     current
    DESCRIPTION
        "Writing this to active(1) creates an entry.
         Writing this to destroy(2) destroys an entry."
    ::= { trapDestEntry 5 }
--********************************************************************************************************
--********************************************************************************************************

--xxx.100.16.1
    arpMgt               		  OBJECT IDENTIFIER ::= { l3 1 }
--xxx.100.16.2
    routeMgt               		  OBJECT IDENTIFIER ::= { l3 2 }    
--xxx.100.16.1.1
        arpCacheDeleteAll OBJECT-TYPE
            SYNTAX  INTEGER  
            	   {
			delete(1), -- trigger clear all arp cache
			noDelete(0)-- when then snmp agent read this node, the value is meaningless
                    }         	
            MAX-ACCESS  read-create
            STATUS  current
            DESCRIPTION
                "when set , triger flush arp-cache, when get ,nosense"
            ::= { arpMgt  1 }

--xxx.100.16.1.2
        arpCacheTimeout OBJECT-TYPE
            SYNTAX  INTEGER                      
            MAX-ACCESS  read-only
            STATUS  current
            DESCRIPTION
                "arp cache timeout time"
            ::= { arpMgt  2 }     
--xxx.100.16.1.3
        arpSecurityUpdateProtectALL OBJECT-TYPE
            SYNTAX  INTEGER 
            	   {
			enable(1),
			disable(0)
                    }                       	
            MAX-ACCESS  read-create
            STATUS  current
            DESCRIPTION
                "global enable or disable arp security update protect"
            ::= { arpMgt  3 }

--xxx.100.16.1.4
        arpSecurityLearnProtectALL OBJECT-TYPE
            SYNTAX  INTEGER 
            	   {
			enable(1),
			disable(0)
                    }               
            MAX-ACCESS  read-create
            STATUS  current
            DESCRIPTION
                "global enable or disable arp security learn protect"
            ::= { arpMgt  4 }  
--xxx.100.16.1.5
        arpSecurityConvertALL OBJECT-TYPE
            SYNTAX  INTEGER   
            	   {
			enable(1),
			disable(0)
                    }                     	
            MAX-ACCESS  read-create
            STATUS  current
            DESCRIPTION
                "global convert dynamic arp-cache to static arp item .enable mean convert"
            ::= { arpMgt  5 }    


--xxx.100.16.1.6
arpSecurityTable OBJECT-TYPE 
    SYNTAX  SEQUENCE OF ArpSecurityEntry
    MAX-ACCESS  not-accessible
    STATUS  current
    DESCRIPTION
        "arp security table"
    ::= { arpMgt   6}
            
--xxx.100.16.1.6.1
arpSecurityEntry OBJECT-TYPE
        SYNTAX  ArpSecurityEntry
        MAX-ACCESS  not-accessible
        STATUS  current
        DESCRIPTION
            " index is L3 interface index"
        INDEX   { arpSecurityIfindex}
        ::= { arpSecurityTable 1 }

ArpSecurityEntry
        ::= SEQUENCE
            {
                arpSecurityIfindex               		INTEGER,
                arpSecurityUpdateProtect			INTEGER,
                arpSecurityLearnProtect				INTEGER,
                arpSecurityConvert				INTEGER
            }
            
--xxx.100.16.1.6.1.1
arpSecurityIfindex  OBJECT-TYPE
            SYNTAX  INTEGER 
            MAX-ACCESS  not-accessible
            STATUS  current
            DESCRIPTION
                "L3 interface index"
            ::= { arpSecurityEntry 1 }
            
--xxx.100.16.1.6.1.2         
arpSecurityUpdateProtect  OBJECT-TYPE
	SYNTAX      INTEGER
            	   {
			enable(1),
			disable(0)
                    }   	
        MAX-ACCESS  read-create
        STATUS      current
        DESCRIPTION 
                "enable or disable arp security update protect on the current port"
        ::= { arpSecurityEntry 2 }
        
--xxx.100.16.1.6.1.3         
arpSecurityLearnProtect  OBJECT-TYPE 
        SYNTAX      INTEGER 
            	   {
			enable(1),
			disable(0)
                    }           
        MAX-ACCESS  read-create
        STATUS      current
        DESCRIPTION 
                "enable or disable arp security learn protect on the current port"
        ::= { arpSecurityEntry 3 }  
--xxx.100.16.1.6.1.4         
arpSecurityConvert  OBJECT-TYPE
        SYNTAX      INTEGER 
            	   {
			enable(1),
			disable(0)
                    }           
        MAX-ACCESS  read-create
        STATUS      current
        DESCRIPTION "convert dynamic arp-cache to static arp item on the port.enable mean convert,get OPS is nosense"
        ::= { arpSecurityEntry 4 }     
        
        

--xxx.100.16.1.7
arpProxyArpTable OBJECT-TYPE 
    SYNTAX  SEQUENCE OF ArpProxyArpEntry
    MAX-ACCESS  not-accessible
    STATUS  current
    DESCRIPTION
        " configure arp proxy list"
    ::= { arpMgt   7}
            
--xxx.100.16.1.7.1
arpProxyArpEntry OBJECT-TYPE
        SYNTAX  ArpProxyArpEntry
        MAX-ACCESS  not-accessible
        STATUS  current
        DESCRIPTION
            " index is L3 interface index"
        INDEX   { arpProxyArpIfIndex}
        ::= { arpProxyArpTable 1 }

ArpProxyArpEntry
        ::= SEQUENCE
            {
                arpProxyArpIfIndex               		INTEGER,
                arpProxyArpStatus				INTEGER
            }
            
--xxx.100.16.1.7.1.1
arpProxyArpIfIndex  OBJECT-TYPE
            SYNTAX  INTEGER 
            MAX-ACCESS  not-accessible
            STATUS  current
            DESCRIPTION
                " L3 interface index"
            ::= { arpProxyArpEntry 1 }
            
--xxx.100.16.1.7.1.2         
arpProxyArpStatus  OBJECT-TYPE
	SYNTAX      INTEGER
            	   {
			enable(1),
			disable(0)
                    }   	
        MAX-ACCESS  read-create
        STATUS      current
        DESCRIPTION "arp proxy enable"
        ::= { arpProxyArpEntry 2 }                 
        
        
--xxx.100.16.1.7
arpStaticTable OBJECT-TYPE 
    SYNTAX  SEQUENCE OF ArpStaticEntry
    MAX-ACCESS  not-accessible
    STATUS  current
    DESCRIPTION
        " static state arp configuration list"
    ::= { arpMgt   8}
            
--xxx.100.16.1.8.1
arpStaticEntry OBJECT-TYPE
        SYNTAX  ArpStaticEntry
        MAX-ACCESS  not-accessible
        STATUS  current
        DESCRIPTION
            " index is 'arpProxyArpIfIndex.arpStaticIpaddress'."
        INDEX   { arpProxyArpIfIndex,arpStaticIpaddress}
        ::= { arpStaticTable 1 }

ArpStaticEntry
        ::= SEQUENCE
            {
                arpStaticIfindex               		INTEGER,
                arpStaticIpaddress			IpAddress,
                arpStaticMac				MacAddress,
                arpStaticPortIndex			INTEGER,
                arpStaticStatus				INTEGER
            }
            
--xxx.100.16.1.8.1.1
arpStaticIfindex  OBJECT-TYPE
            SYNTAX  INTEGER 
            MAX-ACCESS  not-accessible
            STATUS  current
            DESCRIPTION
                " L3 interface index"
            ::= { arpStaticEntry 1 }
            
--xxx.100.16.1.8.1.2         
arpStaticIpaddress  OBJECT-TYPE
	SYNTAX      IpAddress	
        MAX-ACCESS  not-accessible
        STATUS      current
        DESCRIPTION "ip address"
        ::= { arpStaticEntry 2 }  
--xxx.100.16.1.8.1.3
arpStaticMac  OBJECT-TYPE
            SYNTAX  MacAddress 
            MAX-ACCESS  read-create
            STATUS  current
            DESCRIPTION
                " the Mac address of the arp item"
            ::= { arpStaticEntry 3 }
            
--xxx.100.16.1.8.1.4         
arpStaticPortIndex  OBJECT-TYPE
	SYNTAX      INTEGER	
        MAX-ACCESS  read-create
        STATUS      current
        DESCRIPTION "the port index of the arp item"
        ::= { arpStaticEntry 4 }              
--xxx.100.16.1.8.1.5
arpStaticStatus  OBJECT-TYPE
            SYNTAX  INTEGER 
            	{
            		valid(1),--create one arp entry , stand for this arp entry is valid
            		invalid(2), --destory one arp entry , stand for this arp entry is invalid
            		waitingforset(3) -- this is the default status
            	}
            MAX-ACCESS  read-create
            STATUS  current
            DESCRIPTION
                "valid(1),this is a active arp when get/getnext; when set,mean create the static arp item
            		invalid(2); when set, mean destory the current arp item
            		waitingforset(3); reserved"
            ::= { arpStaticEntry 5 }
       
       
       
--xxx.100.16.2.1
ipStaticRouteExtTable OBJECT-TYPE 
    SYNTAX  SEQUENCE OF IpStaticRouteExtEntry
    MAX-ACCESS  not-accessible
    STATUS  current
    DESCRIPTION
        " static route configuration list"
    ::= { routeMgt   1}
            
--xxx.100.16.2.1.1
ipStaticRouteExtEntry OBJECT-TYPE
        SYNTAX  IpStaticRouteExtEntry
        MAX-ACCESS  not-accessible
        STATUS  current
        DESCRIPTION
            "The index of this table is ip.mask"
        INDEX   { ipStaticRouteExtDest,ipStaticRouteExtMask }
        ::= { ipStaticRouteExtTable 1 }

IpStaticRouteExtEntry
        ::= SEQUENCE
            {
                ipStaticRouteExtDest               		IpAddress,
                ipStaticRouteExtMask				IpAddress,
                ipStaticRouteExtNextHop				IpAddress,
                ipStaticRouteExtMetric				INTEGER,
                ipStaticRouteExtStatus				INTEGER
            }
            
--xxx.100.16.2.1.1.1
ipStaticRouteExtDest  OBJECT-TYPE
            SYNTAX  IpAddress 
            MAX-ACCESS  not-accessible
            STATUS  current
            DESCRIPTION
                "static route of intention net segment"
            ::= { ipStaticRouteExtEntry 1 }
            
--xxx.100.16.2.1.1.2         
ipStaticRouteExtMask  OBJECT-TYPE
	SYNTAX      IpAddress	
        MAX-ACCESS  not-accessible
        STATUS      current
        DESCRIPTION "mask"
        ::= { ipStaticRouteExtEntry 2 }  
--xxx.100.16.2.1.1.3
ipStaticRouteExtNextHop  OBJECT-TYPE
            SYNTAX  IpAddress
            MAX-ACCESS  read-create
            STATUS  current
            DESCRIPTION
                " next step ip"
            ::= { ipStaticRouteExtEntry 3 }
            
--xxx.100.16.2.1.1.4         
ipStaticRouteExtMetric  OBJECT-TYPE
	SYNTAX      INTEGER(1..255)	
        MAX-ACCESS  read-create
        STATUS      current
        DESCRIPTION " Manage distance/PRI"
        ::= { ipStaticRouteExtEntry 4 }              
--xxx.100.16.2.1.1.5
ipStaticRouteExtStatus  OBJECT-TYPE
            SYNTAX  INTEGER 
            	{
            		valid(1),
            		invalid(2),
            		waitingforset(3)
            	}
            MAX-ACCESS  read-create
            STATUS  current
            DESCRIPTION
                " When you get/getnext one entry, the meaning of 'valid' is that the static route which you get is 
                valid (or active); when you want to configure one static route, 'valid/creating' stand for setting one 
                entry, and 'invalid/destory' stands for delete the static route."
            ::= { ipStaticRouteExtEntry 5 }            
       
--********************************************************************************************************
--********************************************************************************************************        


dvmrpMgt           OBJECT IDENTIFIER ::= { l3 5 }

dvmrpScalar     OBJECT IDENTIFIER ::= { dvmrpMgt 1 }

dvmrpVersionString OBJECT-TYPE
    SYNTAX     DisplayString
    MAX-ACCESS read-only
    STATUS     current
    DESCRIPTION
            "The router's DVMRP version information.  Similar to
            sysDescr in MIB-II, this is a free-form field which can be
            used to display vendor-specific information."
    ::= { dvmrpScalar 1 }

-- dvmrpScalar 2 was previously used for a global
-- Generation ID.  However, the DVMRP spec changed it to
-- a per-interface parameter.
dvmrpNumRoutes OBJECT-TYPE
    SYNTAX     Gauge32
    MAX-ACCESS read-only
    STATUS     current
    DESCRIPTION
            "The number of entries in the routing table.  This can be
            used to monitor the routing table size."


    ::= { dvmrpScalar 3 }

dvmrpReachableRoutes OBJECT-TYPE
    SYNTAX     Gauge32
    MAX-ACCESS read-only
    STATUS     current
    DESCRIPTION
            "The number of entries in the routing table with non
            infinite metrics.  This can be used to detect network
            partitions by observing the ratio of reachable routes to
            total routes."
    ::= { dvmrpScalar 4 }


-- The DVMRP Interface Table

dvmrpInterfaceTable OBJECT-TYPE
    SYNTAX     SEQUENCE OF DvmrpInterfaceEntry
    MAX-ACCESS not-accessible
    STATUS     current
    DESCRIPTION
            "The (conceptual) table listing the router's multicast-
            capable interfaces."
    ::= { dvmrpMgt 2 }

dvmrpInterfaceEntry OBJECT-TYPE
    SYNTAX     DvmrpInterfaceEntry
    MAX-ACCESS not-accessible
    STATUS     current
    DESCRIPTION
            "An entry (conceptual row) in the dvmrpInterfaceTable.  This
            row augments ipMRouteInterfaceEntry in the IP Multicast MIB,
            where the threshold object resides."
    INDEX      { dvmrpInterfaceIndex }
    ::= { dvmrpInterfaceTable 1 }

DvmrpInterfaceEntry ::= SEQUENCE {
    dvmrpInterfaceIndex                 InterfaceIndex,
    dvmrpInterfaceLocalAddress          IpAddress,
    dvmrpInterfaceMetric                Integer32,
    dvmrpInterfaceStatus                RowStatus,
    dvmrpInterfaceRcvBadPkts            Counter32,
    dvmrpInterfaceRcvBadRoutes          Counter32,
    dvmrpInterfaceSentRoutes            Counter32,
    dvmrpInterfaceKey                   SnmpAdminString,
    dvmrpInterfaceKeyVersion            Integer32,
    dvmrpInterfaceGenerationId          Integer32
}

dvmrpInterfaceIndex OBJECT-TYPE
    SYNTAX     InterfaceIndex
    MAX-ACCESS read-only
    STATUS     current
    DESCRIPTION
            "The ifIndex value of the interface for which DVMRP is
            enabled."
    ::= { dvmrpInterfaceEntry 1 }

dvmrpInterfaceLocalAddress OBJECT-TYPE
    SYNTAX     IpAddress
    MAX-ACCESS read-only
    STATUS     current
    DESCRIPTION
            "The IP address this system will use as a source address on
            this interface.  On unnumbered interfaces, it must be the
            same value as dvmrpInterfaceLocalAddress for some interface
            on the system."
    ::= { dvmrpInterfaceEntry 2 }

dvmrpInterfaceMetric OBJECT-TYPE
    SYNTAX     Integer32 (1..31)
    MAX-ACCESS read-create
    STATUS     current
    DESCRIPTION
            "The distance metric for this interface which is used to
            calculate distance vectors."
    DEFVAL     { 1 }
    ::= { dvmrpInterfaceEntry 3 }

dvmrpInterfaceStatus OBJECT-TYPE
    SYNTAX     RowStatus
    MAX-ACCESS read-create
    STATUS     current
    DESCRIPTION
            "The status of this entry.  Creating the entry enables DVMRP
            on the virtual interface; destroying the entry or setting it
            to notInService disables DVMRP on the virtual interface."
    ::= { dvmrpInterfaceEntry 4 }

dvmrpInterfaceRcvBadPkts OBJECT-TYPE
    SYNTAX     Counter32
    MAX-ACCESS read-only
    STATUS     current
    DESCRIPTION
            "The number of DVMRP messages received on the interface by
            the DVMRP process which were subsequently discarded as
            invalid (e.g. invalid packet format, or a route report from
            an unknown neighbor)."
    ::= { dvmrpInterfaceEntry 5 }

dvmrpInterfaceRcvBadRoutes OBJECT-TYPE
    SYNTAX     Counter32
    MAX-ACCESS read-only
    STATUS     current
    DESCRIPTION
            "The number of routes, in valid DVMRP packets, which were
            ignored because the entry was invalid."
    ::= { dvmrpInterfaceEntry 6 }

dvmrpInterfaceSentRoutes OBJECT-TYPE
    SYNTAX     Counter32
    MAX-ACCESS read-only
    STATUS     current
    DESCRIPTION
            "The number of routes, in DVMRP Report packets, which have
            been sent on this interface.  Together with
            dvmrpNeighborRcvRoutes at a peer, this object is useful for
            detecting routes being lost."
    ::= { dvmrpInterfaceEntry 7 }

dvmrpInterfaceKey OBJECT-TYPE
    SYNTAX     SnmpAdminString
    MAX-ACCESS read-only
    STATUS     current
    DESCRIPTION
            "The (shared) key for authenticating neighbors on this
            interface.  This object is intended solely for the purpose
            of setting the interface key, and MUST be accessible only
            via requests using both authentication and privacy.  The
            agent MAY report an empty string in response to get, get-
            next, get-bulk requests."
    ::= { dvmrpInterfaceEntry 8 }

dvmrpInterfaceKeyVersion OBJECT-TYPE
    SYNTAX     Integer32
    MAX-ACCESS read-only
    STATUS     current
    DESCRIPTION
            "The highest version number of all known interface keys for
            this interface used for authenticating neighbors."
    ::= { dvmrpInterfaceEntry 9 }

dvmrpInterfaceGenerationId OBJECT-TYPE
    SYNTAX     Integer32
    MAX-ACCESS read-only
    STATUS     current
    DESCRIPTION
            "The generation identifier for the interface.  This is used
            by neighboring routers to detect whether the DVMRP routing
            table should be resent."
    ::= { dvmrpInterfaceEntry 10 }

-- The DVMRP Neighbor Table

dvmrpNeighborTable OBJECT-TYPE
    SYNTAX     SEQUENCE OF DvmrpNeighborEntry
    MAX-ACCESS not-accessible
    STATUS     current
    DESCRIPTION
            "The (conceptual) table listing the router's DVMRP
            neighbors, as discovered by receiving DVMRP messages."
    ::= { dvmrpMgt 3 }

dvmrpNeighborEntry OBJECT-TYPE
    SYNTAX     DvmrpNeighborEntry
    MAX-ACCESS not-accessible
    STATUS     current
    DESCRIPTION
            "An entry (conceptual row) in the dvmrpNeighborTable."
    INDEX      { dvmrpNeighborIfIndex, dvmrpNeighborAddress }
    ::= { dvmrpNeighborTable 1 }

DvmrpNeighborEntry ::= SEQUENCE {
    dvmrpNeighborIfIndex         InterfaceIndex,
    dvmrpNeighborAddress         IpAddress,
    dvmrpNeighborUpTime          TimeTicks,
    dvmrpNeighborExpiryTime      TimeTicks,
    dvmrpNeighborGenerationId    Integer32,
    dvmrpNeighborMajorVersion    Integer32,
    dvmrpNeighborMinorVersion    Integer32,
    dvmrpNeighborCapabilities    BITS,
    dvmrpNeighborRcvRoutes       Counter32,
    dvmrpNeighborRcvBadPkts      Counter32,
    dvmrpNeighborRcvBadRoutes    Counter32,
    dvmrpNeighborState           INTEGER
}

dvmrpNeighborIfIndex OBJECT-TYPE
    SYNTAX     InterfaceIndex
    MAX-ACCESS read-only
    STATUS     current
    DESCRIPTION
            "The value of ifIndex for the virtual interface used to
            reach this DVMRP neighbor."
    ::= { dvmrpNeighborEntry 1 }

dvmrpNeighborAddress OBJECT-TYPE
    SYNTAX     IpAddress
    MAX-ACCESS read-only
    STATUS     current
    DESCRIPTION
            "The IP address of the DVMRP neighbor for which this entry
            contains information."
    ::= { dvmrpNeighborEntry 2 }

dvmrpNeighborUpTime OBJECT-TYPE
    SYNTAX     TimeTicks
    MAX-ACCESS read-only
    STATUS     current
    DESCRIPTION
            "The time since this DVMRP neighbor (last) became a neighbor
            of the local router."
    ::= { dvmrpNeighborEntry 3 }

dvmrpNeighborExpiryTime OBJECT-TYPE
    SYNTAX     TimeTicks
    MAX-ACCESS read-only
    STATUS     current
    DESCRIPTION
            "The minimum time remaining before this DVMRP neighbor will
            be aged out."
    ::= { dvmrpNeighborEntry 4 }

dvmrpNeighborGenerationId OBJECT-TYPE
    SYNTAX     Integer32
    MAX-ACCESS read-only
    STATUS     current
    DESCRIPTION
            "The neighboring router's generation identifier."
    ::= { dvmrpNeighborEntry 5 }

dvmrpNeighborMajorVersion OBJECT-TYPE
    SYNTAX     Integer32 (0..255)
    MAX-ACCESS read-only
    STATUS     current
    DESCRIPTION
            "The neighboring router's major DVMRP version number."
    ::= { dvmrpNeighborEntry 6 }

dvmrpNeighborMinorVersion OBJECT-TYPE
    SYNTAX     Integer32 (0..255)
    MAX-ACCESS read-only
    STATUS     current
    DESCRIPTION
            "The neighboring router's minor DVMRP version number."
    ::= { dvmrpNeighborEntry 7 }

dvmrpNeighborCapabilities OBJECT-TYPE
    SYNTAX     BITS {
                   leaf(0),
                   prune(1),
                   generationID(2),
                   mtrace(3),
                   snmp(4),
                   netmask(5)
                   
               }
    MAX-ACCESS read-only
    STATUS     current
    DESCRIPTION
            "This object describes the neighboring router's
            capabilities.  The leaf bit indicates that the neighbor has
            only one interface with neighbors.  The prune bit indicates
            that the neighbor supports pruning.  The generationID bit
            indicates that the neighbor sends its generationID in Probe
            messages.  The mtrace bit indicates that the neighbor can
            handle mtrace requests. The snmp bit indicates that the 
            neighbor support snmp. The netmask bit indicates that the 
            neighbor support netmask."
    ::= { dvmrpNeighborEntry 8 }

dvmrpNeighborRcvRoutes OBJECT-TYPE
    SYNTAX     Counter32
    MAX-ACCESS read-only
    STATUS     current
    DESCRIPTION
            "The total number of routes received in valid DVMRP packets
            received from this neighbor.  This can be used to diagnose
            problems such as unicast route injection, as well as giving
            an indication of the level of DVMRP route exchange
            activity."
    ::= { dvmrpNeighborEntry 9 }

dvmrpNeighborRcvBadPkts OBJECT-TYPE
    SYNTAX     Counter32
    MAX-ACCESS read-only
    STATUS     current
    DESCRIPTION
            "The number of packet received from this neighbor which were
            discarded as invalid."
    ::= { dvmrpNeighborEntry 10 }

dvmrpNeighborRcvBadRoutes OBJECT-TYPE
    SYNTAX     Counter32
    MAX-ACCESS read-only
    STATUS     current
    DESCRIPTION
            "The number of routes, in valid DVMRP packets received from
            this neighbor, which were ignored because the entry was
            invalid."
    ::= { dvmrpNeighborEntry 11 }

dvmrpNeighborState OBJECT-TYPE
    SYNTAX     INTEGER { oneway(1), active(2), ignoring(3), down(4) }
    MAX-ACCESS read-only
    STATUS     current
    DESCRIPTION
            "State of the neighbor adjacency."
    ::= { dvmrpNeighborEntry 12 }


-- The DVMRP Route Table

dvmrpRouteTable OBJECT-TYPE
    SYNTAX     SEQUENCE OF DvmrpRouteEntry
    MAX-ACCESS not-accessible
    STATUS     current
    DESCRIPTION
            "The table of routes learned through DVMRP route exchange."
    ::= { dvmrpMgt 4 }

dvmrpRouteEntry OBJECT-TYPE
    SYNTAX     DvmrpRouteEntry
    MAX-ACCESS not-accessible
    STATUS     current
    DESCRIPTION
            "An entry (conceptual row) containing the multicast routing
            information used by DVMRP in place of the unicast routing
            information."
    INDEX      { dvmrpRouteSource, dvmrpRouteSourceMask }
    ::= { dvmrpRouteTable 1 }

DvmrpRouteEntry ::= SEQUENCE {
    dvmrpRouteSource             IpAddress,
    dvmrpRouteSourceMask         IpAddress,
    dvmrpRouteUpstreamNeighbor   IpAddress,
    dvmrpRouteIfIndex            InterfaceIndexOrZero,
    dvmrpRouteMetric             Integer32,
    dvmrpRouteExpiryTime         TimeTicks,
    dvmrpRouteUpTime             TimeTicks
}

dvmrpRouteSource OBJECT-TYPE
    SYNTAX     IpAddress
    MAX-ACCESS read-only
    STATUS     current
    DESCRIPTION
            "The network address which when combined with the
            corresponding value of dvmrpRouteSourceMask identifies the
            sources for which this entry contains multicast routing
            information."
    ::= { dvmrpRouteEntry 1 }

dvmrpRouteSourceMask OBJECT-TYPE
    SYNTAX     IpAddress
    MAX-ACCESS read-only
    STATUS     current
    DESCRIPTION
            "The network mask which when combined with the corresponding
            value of dvmrpRouteSource identifies the sources for which
            this entry contains multicast routing information."
    ::= { dvmrpRouteEntry 2 }

dvmrpRouteUpstreamNeighbor OBJECT-TYPE
    SYNTAX     IpAddress
    MAX-ACCESS read-only
    STATUS     current
    DESCRIPTION
            "The address of the upstream neighbor (e.g., RPF neighbor)
            from which IP datagrams from these sources are received."
    ::= { dvmrpRouteEntry 3 }

dvmrpRouteIfIndex OBJECT-TYPE
    SYNTAX     InterfaceIndexOrZero
    MAX-ACCESS read-only
    STATUS     current
    DESCRIPTION
            "The value of ifIndex for the interface on which IP
            datagrams sent by these sources are received.  A value of 0
            typically means the route is an aggregate for which no next-
            hop interface exists."
    ::= { dvmrpRouteEntry 4 }

dvmrpRouteMetric OBJECT-TYPE
    SYNTAX     Integer32 (1..32)
    MAX-ACCESS read-only
    STATUS     current
    DESCRIPTION
            "The distance in hops to the source subnet."
    ::= { dvmrpRouteEntry 5 }

dvmrpRouteExpiryTime OBJECT-TYPE
    SYNTAX     TimeTicks
    MAX-ACCESS read-only
    STATUS     current
    DESCRIPTION
            "The minimum amount of time remaining before this entry will
            be aged out."
    ::= { dvmrpRouteEntry 6 }

dvmrpRouteUpTime OBJECT-TYPE
    SYNTAX     TimeTicks
    MAX-ACCESS read-only
    STATUS     current
    DESCRIPTION
            "The time since the route represented by this entry was
            learned by the router."
    ::= { dvmrpRouteEntry 7 }

-- The DVMRP Routing Next Hop Table


dvmrpRouteNextHopTable OBJECT-TYPE
    SYNTAX     SEQUENCE OF DvmrpRouteNextHopEntry
    MAX-ACCESS not-accessible
    STATUS     current
    DESCRIPTION
            "The (conceptual) table containing information on the next
            hops on outgoing interfaces for routing IP multicast
            datagrams."
    ::= { dvmrpMgt 5 }

dvmrpRouteNextHopEntry OBJECT-TYPE
    SYNTAX     DvmrpRouteNextHopEntry
    MAX-ACCESS not-accessible
    STATUS     current
    DESCRIPTION
            "An entry (conceptual row) in the list of next hops on
            outgoing interfaces to which IP multicast datagrams from
            particular sources are routed."
    INDEX      { dvmrpRouteNextHopSource, dvmrpRouteNextHopSourceMask,
                 dvmrpRouteNextHopIfIndex }
    ::= { dvmrpRouteNextHopTable 1 }

DvmrpRouteNextHopEntry ::= SEQUENCE {
    dvmrpRouteNextHopSource             IpAddress,
    dvmrpRouteNextHopSourceMask         IpAddress,
    dvmrpRouteNextHopIfIndex            InterfaceIndex,
    dvmrpRouteNextHopType               INTEGER
}

dvmrpRouteNextHopSource OBJECT-TYPE
    SYNTAX     IpAddress
    MAX-ACCESS read-only
    STATUS     current
    DESCRIPTION
            "The network address which when combined with the
            corresponding value of dvmrpRouteNextHopSourceMask
            identifies the sources for which this entry specifies a next
            hop on an outgoing interface."
    ::= { dvmrpRouteNextHopEntry 1 }

dvmrpRouteNextHopSourceMask OBJECT-TYPE
    SYNTAX     IpAddress
    MAX-ACCESS read-only
    STATUS     current
    DESCRIPTION
            "The network mask which when combined with the corresponding
            value of dvmrpRouteNextHopSource identifies the sources for
            which this entry specifies a next hop on an outgoing
            interface."
    ::= { dvmrpRouteNextHopEntry 2 }

dvmrpRouteNextHopIfIndex OBJECT-TYPE
    SYNTAX     InterfaceIndex
    MAX-ACCESS read-only
    STATUS     current
    DESCRIPTION
            "The ifIndex value of the interface for the outgoing
            interface for this next hop."
    ::= { dvmrpRouteNextHopEntry 3 }

dvmrpRouteNextHopType OBJECT-TYPE
    SYNTAX     INTEGER { leaf(1), branch(2) }
    MAX-ACCESS read-only
    STATUS     current
    DESCRIPTION
            "Type is leaf if no downstream dependent neighbors exist on
            the outgoing virtual interface.  Otherwise, type is branch."
    ::= { dvmrpRouteNextHopEntry 4 }

-- The DVMRP Prune Table

dvmrpPruneTable OBJECT-TYPE
    SYNTAX     SEQUENCE OF DvmrpPruneEntry
    MAX-ACCESS not-accessible
    STATUS     current
    DESCRIPTION
            "The (conceptual) table listing the router's upstream prune
            state."
    ::= { dvmrpMgt 6 }

dvmrpPruneEntry OBJECT-TYPE
    SYNTAX     DvmrpPruneEntry
    MAX-ACCESS not-accessible
    STATUS     current
    DESCRIPTION
            "An entry (conceptual row) in the dvmrpPruneTable."
    INDEX      { dvmrpPruneGroup, dvmrpPruneSource,
                 dvmrpPruneSourceMask }
    ::= { dvmrpPruneTable 1 }

DvmrpPruneEntry ::= SEQUENCE {
    dvmrpPruneGroup              IpAddress,
    dvmrpPruneSource             IpAddress,
    dvmrpPruneSourceMask         IpAddress,
    dvmrpPruneExpiryTime         TimeTicks
}

dvmrpPruneGroup OBJECT-TYPE
    SYNTAX     IpAddress
    MAX-ACCESS read-only
    STATUS     current
    DESCRIPTION
            "The group address which has been pruned."
    ::= { dvmrpPruneEntry 1 }

dvmrpPruneSource OBJECT-TYPE
    SYNTAX     IpAddress
    MAX-ACCESS read-only
    STATUS     current
    DESCRIPTION
            "The address of the source or source network which has been
            pruned."
    ::= { dvmrpPruneEntry 2 }

dvmrpPruneSourceMask OBJECT-TYPE
    SYNTAX     IpAddress
    MAX-ACCESS read-only
    STATUS     current
    DESCRIPTION
            "The address of the source or source network which has been
            pruned.  The mask must either be all 1's, or else
            dvmrpPruneSource and dvmrpPruneSourceMask must match
            dvmrpRouteSource and dvmrpRouteSourceMask for some entry in
            the dvmrpRouteTable."
    ::= { dvmrpPruneEntry 3 }

dvmrpPruneExpiryTime OBJECT-TYPE
    SYNTAX     TimeTicks
    MAX-ACCESS read-only
    STATUS     current
    DESCRIPTION
            "The amount of time remaining before this prune should
            expire at the upstream neighbor.  This value should be the
            minimum of the default prune lifetime and the remaining
            prune lifetimes of the local router's downstream neighbors,
            if any."
    ::= { dvmrpPruneEntry 4 }




ripMgt              OBJECT IDENTIFIER ::= { l3 3 }
ospfMgt             OBJECT IDENTIFIER ::= { l3 4 }
-- ripMgt


ripTimers OBJECT IDENTIFIER ::= { ripMgt 1 }

ripUpdateTime OBJECT-TYPE
        SYNTAX      Integer32 (5..2147483647)
        MAX-ACCESS  read-write
        STATUS      current
        DESCRIPTION "The update time in seconds controls the advertising of regular
                     update messages. The real working model, while using this
                     timer, the time should be offset by a small random time
                     (+/- 0 to 5 seconds each time it is set."
        DEFVAL      { 30 }
        ::= { ripTimers 1 }

ripTimeoutTime OBJECT-TYPE
        SYNTAX      Integer32 (5..2147483647)
        MAX-ACCESS  read-write
        STATUS      current
        DESCRIPTION "The timeout timer in seconds governs the validity of a route.
                     It is initialized when a route is established, and any time
                     an update message is received for the route. If the setting time
                     elapses from the last time the timrout was initialized, the route
                     is considered to have expired, and the hop count of the route is
                     set to infinite. It should be at least three times the value of 
                     update timer."
        DEFVAL      { 180 }
        ::= { ripTimers 2 }

ripGarbageCollectionTime OBJECT-TYPE
        SYNTAX      Integer32 (5..2147483647)
        MAX-ACCESS  read-write
        STATUS      current
        DESCRIPTION "When the information about a route becomes invalid, the system
                     should not immediately purge that route from its table. Instead,
                     it continues to advertise the route with a metric of infinite.
                     At the same time, the garbage-collection timer is set for that 
                     route. When the count reaches zero, the route is purged from the
                     the table. This timer allows neighbors to become aware of 
                     the invalidity of a route prior to purging."
        DEFVAL      { 120 }
        ::= { ripTimers 3 }

ripRoutingProcessStatus OBJECT-TYPE
        SYNTAX      EnabledStatusPrivate
        MAX-ACCESS  read-write
        STATUS      current
        DESCRIPTION "Enable or Disable RIP routing process on a system."
        DEFVAL      { disabled }
        ::= { ripMgt 2 }
        
ripRouterVersion OBJECT-TYPE
        SYNTAX      INTEGER
                    {   
                        rip1(1),
                        rip2(2)
                    }
        MAX-ACCESS  read-write
        STATUS      current
        DESCRIPTION "To specify a RIP version used globally by the rourter."
        DEFVAL      { rip2 }
        ::= { ripMgt 3 }
        


ripInstabilityPreventingTable OBJECT-TYPE
        SYNTAX      SEQUENCE OF RipInstabilityPreventingEntry
        MAX-ACCESS  not-accessible
        STATUS      current
        DESCRIPTION "A list of RIP instability preventing status"
        ::= { ripMgt 4 }

ripInstabilityPreventingEntry OBJECT-TYPE
        SYNTAX      RipInstabilityPreventingEntry
        MAX-ACCESS  not-accessible
        STATUS      current
        DESCRIPTION "An entry in the table, containing information
                     about RIP instability preventing configuration.
                     The ifIndex index is a VLAN's ifIndex"
        INDEX       { ripVlanIndex }
        ::= { ripInstabilityPreventingTable 1 }

RipInstabilityPreventingEntry ::= SEQUENCE
{
    ripVlanIndex             Integer32,
    ripSplitHorizonStatus   INTEGER
}


ripVlanIndex OBJECT-TYPE
        SYNTAX      Integer32
        MAX-ACCESS  read-only
        STATUS      current
        DESCRIPTION "This is defined as a VLAN interface.
                     A routing interface is a VLAN binds a IP
                     subnet."
        ::= { ripInstabilityPreventingEntry 1 }
        
ripSplitHorizonStatus OBJECT-TYPE
        SYNTAX      INTEGER
                    {
                        splitHorizon(2),
                        poisonReverse(0),
                        none(1)
                    }
        MAX-ACCESS  read-write
        STATUS      current
        DESCRIPTION "Enable or Disable RIP instability preventing status on an interface" 
        ::= { ripInstabilityPreventingEntry 2 }


ripStatisticsReset OBJECT-TYPE
        SYNTAX      INTEGER
                    {
                        reset(1),
                        noReset(2)
                    }
        MAX-ACCESS  read-write
        STATUS      current
        DESCRIPTION "Write it to reset(1), the following objects in RFC 1724 
                     should be reset: 
                     1. Global Counters:
                        'rip2GlobalRouteChanges',
                        'rip2GlobalQueries'.
                     2. Interface Status Table, for each 'rip2IfStatAddress':
                        'rip2IfStatRcvBadPackets',
                        'rip2IfStatRcvBadRoutes',
                        'rip2IfStatSendUpdates'
                     3. Peer Table, for each 'rip2PeerAddress' and 'rip2PeerDomain',
                        'rip2PeerRcvBadPackets',
                        'rip2PeerRcvBadRoutes'
                     When read it, this value always is noReset(2)."
        ::= { ripMgt 5 }

ripNetworkInterfaceTable OBJECT-TYPE
        SYNTAX      SEQUENCE OF RipNetworkInterfaceEntry
        MAX-ACCESS  not-accessible
        STATUS      current
        DESCRIPTION ""
        ::= { ripMgt 6 }

ripNetworkInterfaceEntry OBJECT-TYPE
        SYNTAX      RipNetworkInterfaceEntry
        MAX-ACCESS  not-accessible
        STATUS      current
        DESCRIPTION ""
        INDEX       { ripNetworkInterfaceAddress }
        ::= { ripNetworkInterfaceTable 1 }

RipNetworkInterfaceEntry ::= SEQUENCE
{
    ripNetworkInterfaceAddress  IpAddress,
    ripNetworkInterfaceStatus   ValidStatus
}


ripNetworkInterfaceAddress OBJECT-TYPE
        SYNTAX      IpAddress
        MAX-ACCESS  read-only
        STATUS      current
        DESCRIPTION "The RIP Network address(the ip address of the interface)."
        ::= { ripNetworkInterfaceEntry 1 }

             
ripNetworkInterfaceStatus OBJECT-TYPE
        SYNTAX      ValidStatus
        MAX-ACCESS  read-create
        STATUS      current
        DESCRIPTION "Set this variable to create or destroy a RIP network address.
         ValidStatus:
         A simple status value for the object to create and destroy
         a table entry. This is a simplified variant of RowStatus as it
         supports only two values. Setting it to valid(1) creates an entry.
         Setting it to invalid(0) destroys an entry." 
        ::= { ripNetworkInterfaceEntry 2 }
        
ripNetworkAddrTable OBJECT-TYPE
        SYNTAX      SEQUENCE OF RipNetworkAddrEntry
        MAX-ACCESS  not-accessible
        STATUS      current
        DESCRIPTION ""
        ::= { ripMgt 7 }

ripNetworkAddrEntry OBJECT-TYPE
        SYNTAX      RipNetworkAddrEntry
        MAX-ACCESS  not-accessible
        STATUS      current
        DESCRIPTION ""
        INDEX       { ripNetworkAddrAddress,ripNetworkAddrPrefixLen }
        ::= { ripNetworkAddrTable 1 }

RipNetworkAddrEntry ::= SEQUENCE
{
    ripNetworkAddrAddress  IpAddress,
    ripNetworkAddrPrefixLen  INTEGER,
    ripNetworkAddrStatus   INTEGER
}


ripNetworkAddrAddress OBJECT-TYPE
        SYNTAX      IpAddress
        MAX-ACCESS  read-only
        STATUS      current
        DESCRIPTION "The RIP Network address."
        ::= { ripNetworkAddrEntry 1 }
        
ripNetworkAddrPrefixLen OBJECT-TYPE
        SYNTAX      INTEGER (0..32)
        MAX-ACCESS  read-only
        STATUS      current
        DESCRIPTION "The RIP Network prefix length of address."
        ::= { ripNetworkAddrEntry 2 }        

             
ripNetworkAddrStatus OBJECT-TYPE
        SYNTAX INTEGER {     
                valid(1),
                invalid (0)
        }
        MAX-ACCESS  read-create
        STATUS      current
        DESCRIPTION "Set this variable to create or destroy a RIP network address.
         ValidStatus:
         A simple status value for the object to create and destroy
         a table entry. This is a simplified variant of RowStatus as it
         supports only two values. Setting it to valid(1) creates an entry.
         Setting it to invalid(0) destroys an entry." 
        ::= { ripNetworkAddrEntry 3 }        
       
        
-- ospfMgt
       
ospfSystemGroup OBJECT IDENTIFIER ::= { ospfMgt 1 } 
    
ospfRouterIdType OBJECT-TYPE
        SYNTAX      INTEGER
                    {
                        auto(1),
                        manual(2)
                    }
        MAX-ACCESS  read-only
        STATUS      current
        DESCRIPTION "Set router ID automatically or  manually."
        DEFVAL { auto }
        ::= { ospfSystemGroup 1 }
 
ospfRfc1583CompatibleState OBJECT-TYPE
        SYNTAX      EnabledStatusPrivate
        MAX-ACCESS  read-write
        STATUS      current
        DESCRIPTION 	"Enable or disable rfc1583 compatibility."
        DEFVAL { disabled }
        ::= { ospfSystemGroup 2 }
 
ospfAutoCost OBJECT-TYPE
        SYNTAX   Integer32 (1..4294967)
        MAX-ACCESS  read-write
        STATUS      current
        DESCRIPTION "Set the reference bandwith of auto cost, the unit is Mbps."
        DEFVAL { 100 }
        ::= { ospfSystemGroup 3 }
       
ospfAdvertiseDefaultRoute OBJECT-TYPE
        SYNTAX   INTEGER
            {
                   disable(0),
                   always(1),
                   notAlways(2)
                }
        MAX-ACCESS  read-write
        STATUS      current
        DESCRIPTION 	"If always is set, always advertises the default route regardless 
                     	of whether the default route exists;If notalways is set ,advertises 
                     	the default route when the router have the default route."
        DEFVAL { disable }
        ::= { ospfSystemGroup 4 }    
     
 
ospfDefaultExternalMetric OBJECT-TYPE
        SYNTAX      OspfBigMetric
        MAX-ACCESS  read-write
        STATUS      current
        DESCRIPTION "Metric used for generating the default route."
        ::= { ospfSystemGroup 5 }    
 
ospfSpfHoldTime OBJECT-TYPE
        SYNTAX   Unsigned32 (0..4294967295)
        MAX-ACCESS  read-write
        STATUS      current
        DESCRIPTION 	"Sets the hold time between two consecutive SPF calculations."
        DEFVAL { 10 }
        ::= { ospfSystemGroup 6 }  

ospfSpfDelayTime OBJECT-TYPE
        SYNTAX   Unsigned32 (0..4294967295)
        MAX-ACCESS  read-write
        STATUS      current
        DESCRIPTION	"Sets the delay time to calculate SPF Delay time, in seconds, between 
                         when OSPF receives a topology change and when it starts an SPF calculation." 
        DEFVAL { 5 }
        ::= { ospfSystemGroup 7 }  
        
ospfAreaNumber OBJECT-TYPE
        SYNTAX   Integer32
        MAX-ACCESS  read-only
        STATUS      current
        DESCRIPTION	"Records the OSPF area numbers." 
              
        DEFVAL { 0 }
        ::= { ospfSystemGroup 8 }      
         
clearOspfProcess OBJECT-TYPE
        SYNTAX   Integer32(0..65535)
        MAX-ACCESS  read-write
        STATUS      current
        DESCRIPTION	"clear ip ospf process by process ID." 
        DEFVAL { 0 }
        ::= { ospfSystemGroup 9 }    
         
ospfNssaTable OBJECT-TYPE
        SYNTAX   SEQUENCE OF OspfNssaEntry
        MAX-ACCESS   not-accessible
        STATUS   current
        DESCRIPTION
           "A conceptually table for ospfNssaEntry."       
        ::= {ospfMgt 2 }

ospfNssaEntry OBJECT-TYPE
        SYNTAX   OspfNssaEntry
        MAX-ACCESS   not-accessible
        STATUS   current
        DESCRIPTION
           "A conceptually row for ospfNssaTable."      
      INDEX { ospfNssaAreaId }
      ::= { ospfNssaTable 1 }

OspfNssaEntry ::= SEQUENCE 
      {
        ospfNssaAreaId                     OspfAreaID,
        ospfNssaStatus                     EnabledStatusPrivate,
        ospfNssaRedistributeStatus         EnabledStatusPrivate,
        ospfNssaOriginateDefaultInfoStatus EnabledStatusPrivate

      }

ospfNssaAreaId OBJECT-TYPE
        SYNTAX       OspfAreaID
        MAX-ACCESS   read-only
        STATUS       current
        DESCRIPTION	"The 32-bit identifier for the NSSA. On creation, 
            this can be derived from the instance."
       ::= { ospfNssaEntry 1 }

ospfNssaStatus OBJECT-TYPE
        SYNTAX       EnabledStatusPrivate
        MAX-ACCESS   read-create
        STATUS       current
        DESCRIPTION
			"The status of this conceptual row entry. This object isused to manage the
			creation and deletion of conceptual rows."
			      
       ::= { ospfNssaEntry 2 }       

ospfNssaRedistributeStatus OBJECT-TYPE
        SYNTAX       EnabledStatusPrivate
        MAX-ACCESS   read-create
        STATUS       current
        DESCRIPTION
           "Enabled or disabled to import routes only into the normal areas,
            but not into the NSSA area."
        DEFVAL { enabled }
       ::= { ospfNssaEntry 3 }

ospfNssaOriginateDefaultInfoStatus OBJECT-TYPE
        SYNTAX       EnabledStatusPrivate
        MAX-ACCESS   read-create        
        STATUS       current
        DESCRIPTION	"Enable or disable to generate a Type 7 default into the NSSA area."
           
         DEFVAL { disabled }   
       ::= { ospfNssaEntry 4 }


       
ospfRedistributeTable OBJECT-TYPE
        SYNTAX   SEQUENCE OF OspfRedistributeEntry
        MAX-ACCESS   not-accessible
        STATUS   current
        DESCRIPTION
           "The conceptual table of all of ospfRedistributeEntry."        
        ::= {ospfMgt 3 }


ospfRedistributeEntry OBJECT-TYPE
        SYNTAX       OspfRedistributeEntry
        MAX-ACCESS   not-accessible
        STATUS       current
        DESCRIPTION
           "The conceptual row for ospfRedistributeTable."      
      INDEX { ospfRedistributeProtocol }
      ::= { ospfRedistributeTable 1 }

OspfRedistributeEntry ::= SEQUENCE 
{
         ospfRedistributeProtocol   INTEGER,
         ospfRedistributeStatus     EnabledStatusPrivate,         
         ospfRedistributeMetricType INTEGER,
         ospfRedistributeMetric     OspfBigMetric

}
 
ospfRedistributeProtocol OBJECT-TYPE
        SYNTAX      INTEGER
                {
                  kernel(1),
                  connect(2),
                  static(3),
                  rip(4),
                  ospf(6),
                  bgp(8),
                  isis(9)
                }
        MAX-ACCESS   read-only
        STATUS       current
        DESCRIPTION	"Protocol ID."
           
       ::= { ospfRedistributeEntry 1 }

ospfRedistributeStatus OBJECT-TYPE
        SYNTAX       EnabledStatusPrivate
        MAX-ACCESS   read-create
        STATUS       current
        DESCRIPTION
			" enable-- redistribute the specific route,disable--- does not redistribute the specific route.For example
			 when the ospfRedistributeProtocol is equal to rip, 'enable' stands for redistribute the route from rip."          
       ::= { ospfRedistributeEntry 2 }  

ospfRedistributeMetricType OBJECT-TYPE
        SYNTAX      INTEGER
                {
                      type1(1),
              				type2(2)
                    }
        MAX-ACCESS   read-create
        STATUS       current
        DESCRIPTION
           "Metric type."
        DEFVAL {type2}
       ::= { ospfRedistributeEntry 3 }

ospfRedistributeMetric OBJECT-TYPE
        SYNTAX       OspfBigMetric
        MAX-ACCESS   read-create
        STATUS       current
        DESCRIPTION
           "Metric value."  
       ::= { ospfRedistributeEntry 4 }


       
ospfSummaryAddressTable OBJECT-TYPE
        SYNTAX   SEQUENCE OF OspfSummaryAddressEntry
        MAX-ACCESS   not-accessible
        STATUS   current
        DESCRIPTION
           "The conceptual table of all of ospfSummaryAddressEntry."     
      ::= {ospfMgt 4}

ospfSummaryAddressEntry OBJECT-TYPE
       SYNTAX       OspfSummaryAddressEntry
       MAX-ACCESS   not-accessible
       STATUS       current
       DESCRIPTION
           "The conceptual row for ospfSummaryAddressTable."      
       INDEX { ospfSummaryAddress,ospfSummaryMask }
       ::= { ospfSummaryAddressTable 1 }

OspfSummaryAddressEntry ::= SEQUENCE 
{
       ospfSummaryAddress   IpAddress,
       ospfSummaryMask      IpAddress,
       ospfSummaryStatus    EnabledStatusPrivate
}
 
ospfSummaryAddress OBJECT-TYPE
        SYNTAX       IpAddress
        MAX-ACCESS   read-only
        STATUS       current
        DESCRIPTION
           "Summary address."
        ::= { ospfSummaryAddressEntry 1 }

ospfSummaryMask OBJECT-TYPE
        SYNTAX       IpAddress
        MAX-ACCESS   read-only
        STATUS       current
        DESCRIPTION
           "Summary mask."
       ::= { ospfSummaryAddressEntry 2 }


ospfSummaryStatus OBJECT-TYPE
        SYNTAX       EnabledStatusPrivate
        MAX-ACCESS   read-create
        STATUS       current
        DESCRIPTION
			" valid/enable--- define a summary, invalid/disable destory the summary from the router"        
       ::= { ospfSummaryAddressEntry 3 }   

ospfNetworkAreaAddressTable OBJECT-TYPE
        SYNTAX   SEQUENCE OF OspfNetworkAreaAddressEntry
        MAX-ACCESS   not-accessible
        STATUS   current
        DESCRIPTION
           "The conceptual table of all of ospfNetworkAreaAddressEntry."     
        ::= {ospfMgt 5 }

ospfNetworkAreaAddressEntry OBJECT-TYPE
        SYNTAX       OspfNetworkAreaAddressEntry
        MAX-ACCESS   not-accessible
        STATUS       current
        DESCRIPTION
           "The conceptual row for ospfNetworkAreaAddressTable."       
        INDEX { ospfNetworkAareaAddress,ospfNetworkAreaMask,ospfNetworkAreaAreaId }
        ::= { ospfNetworkAreaAddressTable 1 }

OspfNetworkAreaAddressEntry ::= SEQUENCE
{
       ospfNetworkAareaAddress  IpAddress,
       ospfNetworkAreaMask      IpAddress,
       ospfNetworkAreaAreaId    IpAddress,     
       ospfNetworkAreaStatus    EnabledStatusPrivate
}
 
ospfNetworkAareaAddress OBJECT-TYPE
        SYNTAX       IpAddress
        MAX-ACCESS   read-only
        STATUS       current
        DESCRIPTION
           "NetworkArea address."
       ::= { ospfNetworkAreaAddressEntry 1 }

ospfNetworkAreaMask OBJECT-TYPE
        SYNTAX   IpAddress
        MAX-ACCESS   read-only
        STATUS   current
        DESCRIPTION
           "NetworkArea mask."
       ::= { ospfNetworkAreaAddressEntry 2 }
    
ospfNetworkAreaAreaId OBJECT-TYPE
        SYNTAX       IpAddress
        MAX-ACCESS   read-only
        STATUS       current
        DESCRIPTION
           "NetworkArea area ID."
       ::= { ospfNetworkAreaAddressEntry 3 }

ospfNetworkAreaStatus OBJECT-TYPE
        SYNTAX       EnabledStatusPrivate
        MAX-ACCESS   read-create
        STATUS       current
        DESCRIPTION
			"enabled(1), disabled(0).
			valid/enable--- run the ospf on the interfaces,which match the ipaddr/mask;
			invalid/disable--disable the ospf.
			 ValidStatus:
         A simple status value for the object to create and destroy
         a table entry. This is a simplified variant of RowStatus as it
         supports only two values. Setting it to valid(1) creates an entry.
         Setting it to invalid(0) destroys an entry." 
       ::= { ospfNetworkAreaAddressEntry 4 }   
       
                          
--********************************************************************************************************
--********************************************************************************************************  

sntpPollTime OBJECT-TYPE
        SYNTAX      INTEGER(16..16284)
        MAX-ACCESS  read-write
        STATUS      current
        DESCRIPTION "The interval for SNTP clients to send requests to NTP/SNTP."
        ::= { sntpMgt 1 }
        
--********************************************************************************************************

sntpServerTable OBJECT-TYPE
    SYNTAX     SEQUENCE OF SntpServerEntry
    MAX-ACCESS not-accessible
    STATUS     current
    DESCRIPTION
           "The ipv4 sntp server configration table."
    ::= { sntpMgt 2 }
    
sntpServerEntry OBJECT-TYPE
    SYNTAX     SntpServerEntry
    MAX-ACCESS not-accessible
    STATUS     current
    DESCRIPTION
            "A set of configuration parameters for a ipv4 sntp server."
    INDEX      {sntpServerVersion,sntpServerAddress}
    ::= { sntpServerTable 1 }

SntpServerEntry
        ::= SEQUENCE
            {
                sntpServerVersion         INTEGER,          
                sntpServerAddress         IpAddress,
                sntpServerStatus	  INTEGER
            }

sntpServerVersion  OBJECT-TYPE
            SYNTAX      INTEGER   (1..4)    
            MAX-ACCESS  read-only
            STATUS      current
            DESCRIPTION
                "The version of ipv4 sntp server."
            ::= { sntpServerEntry 1}        

sntpServerAddress   OBJECT-TYPE
            SYNTAX      IpAddress     
            MAX-ACCESS  read-only
            STATUS      current
            DESCRIPTION
                "The ipv4 address of the sntp server."
            ::= { sntpServerEntry 2}            
                      

sntpServerStatus OBJECT-TYPE
             SYNTAX      INTEGER 
                 {
            	    active(1),
            	    destroy (2)              	
            	}     
            MAX-ACCESS  read-create
            STATUS      current
            DESCRIPTION
                "Now state."
            ::= { sntpServerEntry 3 } 
            
sntpServer6Table OBJECT-TYPE
    SYNTAX     SEQUENCE OF SntpServer6Entry
    MAX-ACCESS not-accessible
    STATUS     current
    DESCRIPTION
           "The ipv6 sntp server configration table."
    ::= { sntpMgt 3 }
    
sntpServer6Entry OBJECT-TYPE
    SYNTAX     SntpServer6Entry
    MAX-ACCESS not-accessible
    STATUS     current
    DESCRIPTION
            "A set of configuration parameters for a ipv6 sntp server."
    INDEX      {sntpServer6Version,sntpServer6Address}
    ::= { sntpServer6Table 1 }

SntpServer6Entry
        ::= SEQUENCE
            {
                sntpServer6Version         INTEGER,           
                sntpServer6Address         Ipv6Address,
                sntpServer6Status	  INTEGER
            } 
                 
sntpServer6Version  OBJECT-TYPE
            SYNTAX      INTEGER   (1..4)    
            MAX-ACCESS  read-only
            STATUS      current
            DESCRIPTION
                "The version of ipv6 sntp server."
            ::= { sntpServer6Entry 1}  

sntpServer6Address   OBJECT-TYPE
            SYNTAX      Ipv6Address     
            MAX-ACCESS  read-only
            STATUS      current
            DESCRIPTION
                "The IP address of the ipv6 sntp server."
            ::= { sntpServer6Entry 2}                              

sntpServer6Status OBJECT-TYPE
             SYNTAX      INTEGER 
                 {
            	    active(1),
            	    destroy (2)              	
            	}     
            MAX-ACCESS  read-create
            STATUS      current
            DESCRIPTION
                "Now state."
            ::= { sntpServer6Entry 3 }             

sntpTimeZone                    OBJECT IDENTIFIER ::= { sntpMgt 4 }

sntpTimeZoneName OBJECT-TYPE
    SYNTAX      DisplayString
    MAX-ACCESS  read-write
    STATUS      current
    DESCRIPTION "The name of sntp time zone."
    ::= { sntpTimeZone 1 }

sntpTimeZoneType OBJECT-TYPE
    SYNTAX      INTEGER
    		{
    			add(1),
    			subtract(0)
    		}
    MAX-ACCESS  read-write
    STATUS      current
    DESCRIPTION "The type of sntp time zone."
    ::= { sntpTimeZone 2 }

sntpTimeZoneTime OBJECT-TYPE
    SYNTAX      INTEGER(0..12)
    MAX-ACCESS  read-write
    STATUS      current
    DESCRIPTION "The interval time of sntp time zone."
    ::= { sntpTimeZone 3 }
     
sntpTimeZoneStatus OBJECT-TYPE
    SYNTAX      INTEGER
    		{
            	    	createAndGo(0),
               		active(1),
               		destroy(2)
               	}	    
    MAX-ACCESS  read-write
    STATUS      current
    DESCRIPTION "now state of sntp time zone."
    ::= { sntpTimeZone 4 }    

--********************************************************************************************************
--******************************************************************************************************** 
--xxx.100.18.1 Urpf 

urpfEnable OBJECT-TYPE
        SYNTAX  INTEGER {
                enable (1),
                disable (0)
            }
        MAX-ACCESS  read-write
        STATUS      current
        DESCRIPTION " Global Enable or disable the Unicast reverse path forwarding."
        ::= { urpf 1 }
        
-- The Urpf Interface Configration Table

urpfPortTable OBJECT-TYPE
    SYNTAX     SEQUENCE OF UrpfPortEntry
    MAX-ACCESS not-accessible
    STATUS     current
    DESCRIPTION
           "The URPF port configration table."
    ::= { urpf 2 }
    
--xxx.100.18.1.1
urpfPortEntry OBJECT-TYPE
    SYNTAX     UrpfPortEntry
    MAX-ACCESS not-accessible
    STATUS     current
    DESCRIPTION
            "The index of this table is port index."
    INDEX      { urpfPortIndex }
    ::= { urpfPortTable 1 }

UrpfPortEntry
        ::= SEQUENCE
            {
                urpfPortIndex              INTEGER,
                urpfPortMode                 INTEGER,
                urpfPortAllowDefault         INTEGER,
                urpfPortStatus		           INTEGER
            }
       
--xxx.100.18.1.1.1
urpfPortIndex  OBJECT-TYPE
            SYNTAX      INTEGER 
            MAX-ACCESS  read-only
            STATUS      current
            DESCRIPTION
                "Port Index."
            ::= { urpfPortEntry 1 }

--xxx.100.18.1.1.2
urpfPortMode   OBJECT-TYPE
            SYNTAX      INTEGER 
             {
            		  loose(1),
            	   strict(0)               	
            	}     
            MAX-ACCESS  read-create
            STATUS      current
            DESCRIPTION
                "Configration of the URPF mode on the port."
            ::= { urpfPortEntry 2}            
                    
--xxx.100.18.1.1.3
urpfPortAllowDefault  OBJECT-TYPE
            SYNTAX      INTEGER 
            {
            		     allowdefaultroute(1),
            	       noallowdefaultroute(0)               	
            	}     
            MAX-ACCESS  read-create
            STATUS      current
            DESCRIPTION
                "Allow or not allow default route of URPF."
            ::= { urpfPortEntry 3}   

--xxx.100.18.1.1.4
urpfPortStatus OBJECT-TYPE
             SYNTAX      INTEGER 
              {
            		  active(1),
            	    destroy (2)              	
            	}     
            MAX-ACCESS  read-create
            STATUS      current
            DESCRIPTION
                "Setting it to  active(1) to creates an entry,setting it to destroy(2) to destroy an entry."
            ::= { urpfPortEntry 4 }            
--********************************************************************************************************
--******************************************************************************************************** 


--xxx.100.20.1 Dcscm dc

-- The Dcscm dc Enable Table

dcscmdcEnable OBJECT-TYPE
    SYNTAX     INTEGER
    {
        disable(0),
        enable(1)
    }
    MAX-ACCESS read-write
    STATUS     current
    DESCRIPTION
           "Dcscm destination control multicast is disable or enable"
    ::= { dcscm 1 }

--xxx.100.20.2

-- The Dcscm dc Acl Table

dcscmdcAclTable OBJECT-TYPE
    SYNTAX     SEQUENCE OF DcscmdcAclEntry
    MAX-ACCESS not-accessible
    STATUS     current
    DESCRIPTION
           "dcscm dst control multicast"
    ::= { dcscm 2 }
            
--xxx.100.20.2.1
dcscmdcAclEntry OBJECT-TYPE
    SYNTAX     DcscmdcAclEntry 
    MAX-ACCESS not-accessible
    STATUS     current
    DESCRIPTION
            "dcscm dst control multicast entry"
    INDEX      { dcscmdcAclNumber,dcscmdcAclSubNumber }
    ::= { dcscmdcAclTable 1 }
    DcscmdcAclEntry
        ::= SEQUENCE
            {
               dcscmdcAclNumber  INTEGER,
               dcscmdcAclSubNumber  INTEGER,
               dcscmdcAclSourceIp  IpAddress,
               dcscmdcAclSourceMask  IpAddress,
               dcscmdcAclDestinationIp  IpAddress,
               dcscmdcAclDestinationMask  IpAddress,
               dcscmdcAclPermitOrDeny  INTEGER
            }

--xxx.100.20.2.1.1
dcscmdcAclNumber  OBJECT-TYPE
            SYNTAX      INTEGER  (6000..7999)
            MAX-ACCESS  read-create
            STATUS      current
            DESCRIPTION
                "Acl number of Dcscm destination control multicast,the range is 6000--7999."
            ::= { dcscmdcAclEntry 1 }

--xxx.100.20.2.1.2
dcscmdcAclSubNumber  OBJECT-TYPE
            SYNTAX      INTEGER  (1..1024)
            MAX-ACCESS  read-create
            STATUS      current
            DESCRIPTION
                "Acl sub number of Dcscm destination control multicast,the range is 1--1024."
            ::= { dcscmdcAclEntry 2 }
            
--xxx.100.20.2.1.3
dcscmdcAclSourceIp  OBJECT-TYPE
            SYNTAX      IpAddress 
            MAX-ACCESS  read-create
            STATUS      current
            DESCRIPTION
                "Source ip address of acl entry "
            ::= { dcscmdcAclEntry 3}  
      
--xxx.100.20.2.1.4
dcscmdcAclSourceMask  OBJECT-TYPE
            SYNTAX      IpAddress 
            MAX-ACCESS  read-create
            STATUS      current
            DESCRIPTION
                "Source Mask of acl entry "
            ::= { dcscmdcAclEntry 4}        

--xxx.100.20.2.1.5
dcscmdcAclDestinationIp  OBJECT-TYPE
            SYNTAX      IpAddress 
            MAX-ACCESS  read-create
            STATUS      current
            DESCRIPTION
                "Destination ip address of acl entry.the destination ip must be a valid multicast group address. "
            ::= { dcscmdcAclEntry 5}              
            
--xxx.100.20.2.1.6
dcscmdcAclDestinationMask  OBJECT-TYPE
            SYNTAX      IpAddress 
            MAX-ACCESS  read-create
            STATUS      current
            DESCRIPTION
                "Destination Mask of acl entry. the destination mask should meet the request of muticast group address. "
            ::= { dcscmdcAclEntry 6} 

--xxx.100.20.2.1.7
dcscmdcAclPermitOrDeny  OBJECT-TYPE
            SYNTAX      INTEGER  
            {
            permit(1),
            deny(0),
            deltheAcl(2)
            }
            MAX-ACCESS  read-write
            STATUS      current
            DESCRIPTION
                " acl entry permit or deny ; 0:deny; 1:permit; 2:del this acl entry"
            ::= { dcscmdcAclEntry 7}    
 
--xxx.100.20.3

-- The DCSCM VMac Destination binding Table

dcscmVMacbindingTable OBJECT-TYPE
    SYNTAX     SEQUENCE OF DcscmVMacbindingEntry
    MAX-ACCESS not-accessible
    STATUS     current
    DESCRIPTION
           "dcscm destination control multicast, Acl is binded to VMac"
    ::= { dcscm 3 }
--xxx.100.20.3.1
dcscmVMacbindingEntry OBJECT-TYPE
    SYNTAX     DcscmVMacbindingEntry
    MAX-ACCESS not-accessible
    STATUS     current
    DESCRIPTION
            "The index of this table is Vlanid,MacAddress"
    INDEX      { dcscmVMacbindingVlanid,dcscmVMacbindingMacAddr }
    ::= { dcscmVMacbindingTable 1 }

DcscmVMacbindingEntry
        ::= SEQUENCE
            {
                dcscmVMacbindingVlanid            INTEGER,
                dcscmVMacbindingMacAddr           MacAddress,
                dcscmVMacbindingAclNumber         INTEGER
            }
            
--xxx.100.20.3.1.1
dcscmVMacbindingVlanid  OBJECT-TYPE
            SYNTAX      INTEGER  (1..4094) 
            MAX-ACCESS  read-only
            STATUS      current
            DESCRIPTION
                " Dcscm destination control multicast,The vlanid of rule"
            ::= { dcscmVMacbindingEntry 1 }  
 
--xxx.100.20.3.1.2
dcscmVMacbindingMacAddr  OBJECT-TYPE
            SYNTAX      MacAddress 
            MAX-ACCESS  read-only
            STATUS      current
            DESCRIPTION
                " Dcscm destination control multicast,The Mac Address of rule"
            ::= { dcscmVMacbindingEntry 2 }    
            
--xxx.100.20.3.1.3
dcscmVMacbindingAclNumber  OBJECT-TYPE
            SYNTAX      INTEGER  (0|6000..7999)
            MAX-ACCESS  read-write
            STATUS      current
            DESCRIPTION
                " Dcscm destination control multicast,The Acl number of rule ; 0 means del the rule binded to vmac"
            ::= { dcscmVMacbindingEntry 3 }                                

--xxx.100.20.4

-- The DCSCM Sip Destination binding Table

dcscmSipbindingTable OBJECT-TYPE
    SYNTAX     SEQUENCE OF DcscmSipbindingEntry
    MAX-ACCESS not-accessible
    STATUS     current
    DESCRIPTION
           "dcscm destination control multicast, Acl is binded to Sip"
    ::= { dcscm 4 }    
--xxx.100.20.4.1
dcscmSipbindingEntry OBJECT-TYPE
    SYNTAX     DcscmSipbindingEntry
    MAX-ACCESS not-accessible
    STATUS     current
    DESCRIPTION
            "The index of this table is Sourceip,SourceMask "
    INDEX      { dcscmSipbindingSipAddress,dcscmSipbindingSipMask }
    ::= { dcscmSipbindingTable 1 }

DcscmSipbindingEntry
        ::= SEQUENCE
            {
                dcscmSipbindingSipAddress           IpAddress,
                dcscmSipbindingSipMask              INTEGER,
                dcscmSipbindingAclNumber         INTEGER
            }
            
--xxx.100.20.4.1.1
dcscmSipbindingSipAddress  OBJECT-TYPE
            SYNTAX      IpAddress 
            MAX-ACCESS  read-only
            STATUS      current
            DESCRIPTION
                " Dcscm destination control multicast,The Source ip of rule"
            ::= { dcscmSipbindingEntry 1 }  
 
--xxx.100.20.4.1.2
dcscmSipbindingSipMask  OBJECT-TYPE
            SYNTAX      INTEGER 
            MAX-ACCESS  read-only
            STATUS      current
            DESCRIPTION
                " Dcscm destination control multicast,The Source ip mask len of rule"
            ::= { dcscmSipbindingEntry 2 }    
            
--xxx.100.20.4.1.3
dcscmSipbindingAclNumber  OBJECT-TYPE
            SYNTAX      INTEGER   (0|6000..7999)
            MAX-ACCESS  read-write
            STATUS      current
            DESCRIPTION
                " Dcscm destination control multicast,The Acl number of rule;0 means del the rule binded to sip"
            ::= { dcscmSipbindingEntry 3 }
            
--xxx.100.20.5

-- The DCSCM Port Destination binding Table

dcscmdcPortbindingTable OBJECT-TYPE
    SYNTAX     SEQUENCE OF DcscmdcPortbindingEntry
    MAX-ACCESS not-accessible
    STATUS     current
    DESCRIPTION
           "dcscm destination control multicast, Acl is binded to Port"
    ::= { dcscm 5 }
--xxx.100.20.5.1
dcscmdcPortbindingEntry OBJECT-TYPE
    SYNTAX     DcscmdcPortbindingEntry
    MAX-ACCESS not-accessible
    STATUS     current
    DESCRIPTION
            "The index of this table is PortName"
    INDEX      { dcscmdcPortbindingPortName }
    ::= { dcscmdcPortbindingTable 1 }

DcscmdcPortbindingEntry
        ::= SEQUENCE
            {
                dcscmdcPortbindingPortName           INTEGER,
                dcscmdcPortbindingAclNumber         INTEGER
            }
            
--xxx.100.20.5.1.1
dcscmdcPortbindingPortName  OBJECT-TYPE
            SYNTAX      INTEGER
            MAX-ACCESS  read-only
            STATUS      current
            DESCRIPTION
                " Dcscm destination control multicast,The Port index of rule"
            ::= { dcscmdcPortbindingEntry 1 }  
 
--xxx.100.20.5.1.2
dcscmdcPortbindingAclNumber  OBJECT-TYPE
            SYNTAX      INTEGER  (0|6000..7999)
            MAX-ACCESS  read-write
            STATUS      current
            DESCRIPTION
                " Dcscm destination control multicast,The Acl number of rule;0 means del the rule binded to port"
            ::= { dcscmdcPortbindingEntry 2 }  
            
--xxx.100.20.6 Dcscm sc

-- The Dcscm sc Enable Table

dcscmscEnable OBJECT-TYPE
    SYNTAX     INTEGER
    {
        disable(0),
        enable(1)
    }
    MAX-ACCESS read-write
    STATUS     current
    DESCRIPTION
           "dcscm source control multicast is disable or enable"
    ::= { dcscm 6 }

--xxx.100.20.7

-- The DCSCM Sc Acl Table

dcscmscAclTable OBJECT-TYPE
    SYNTAX     SEQUENCE OF DcscmscAclEntry
    MAX-ACCESS not-accessible
    STATUS     current
    DESCRIPTION
           "dcscm src control multicast"
    ::= { dcscm 7 }
--xxx.100.20.7.1
dcscmscAclEntry OBJECT-TYPE
    SYNTAX     DcscmscAclEntry 
    MAX-ACCESS not-accessible
    STATUS     current
    DESCRIPTION
            "dcscm src control multicast entry"
    INDEX      { dcscmscAclNumber,dcscmscAclSubNumber }
    ::= { dcscmscAclTable 1 }
    DcscmscAclEntry
        ::= SEQUENCE
            {
               dcscmscAclNumber  INTEGER,
               dcscmscAclSubNumber  INTEGER,
               dcscmscAclSourceIp  IpAddress,
               dcscmscAclSourceMask  IpAddress,
               dcscmscAclDestinationIp  IpAddress,
               dcscmscAclDestinationMask  IpAddress,
               dcscmscAclPermitOrDeny  INTEGER
            }

            
--xxx.100.20.7.1.1
dcscmscAclNumber  OBJECT-TYPE
            SYNTAX      INTEGER (5000..5099)
            MAX-ACCESS  read-write
            STATUS      current
            DESCRIPTION
                "Acl number of Dcscm source control multicast,the range is 5000--5099."
            ::= { dcscmscAclEntry 1 }

--xxx.100.20.7.1.2
dcscmscAclSubNumber  OBJECT-TYPE
            SYNTAX      INTEGER (1..1024)
            MAX-ACCESS  read-write
            STATUS      current
            DESCRIPTION
                "Acl sub number"
            ::= { dcscmscAclEntry 2}  
            
--xxx.100.20.7.1.3
dcscmscAclSourceIp  OBJECT-TYPE
            SYNTAX      IpAddress 
            MAX-ACCESS  read-write
            STATUS      current
            DESCRIPTION
                "Source ip address of acl entry "
            ::= { dcscmscAclEntry 3}  
      
--xxx.100.20.7.1.4
dcscmscAclSourceMask  OBJECT-TYPE
            SYNTAX      IpAddress 
            MAX-ACCESS  read-write
            STATUS      current
            DESCRIPTION
                "Source Mask of acl entry "
            ::= { dcscmscAclEntry 4}        

--xxx.100.20.7.1.5
dcscmscAclDestinationIp  OBJECT-TYPE
            SYNTAX      IpAddress 
            MAX-ACCESS  read-write
            STATUS      current
            DESCRIPTION
                "Destination ip address of acl entry, the destination ip must be a valid multicast group address."
            ::= { dcscmscAclEntry 5}              
            
--xxx.100.20.7.1.6
dcscmscAclDestinationMask  OBJECT-TYPE
            SYNTAX      IpAddress 
            MAX-ACCESS  read-write
            STATUS      current
            DESCRIPTION
                "Destination Mask of acl entry, the destination mask should meet the request of muticast group address."
            ::= { dcscmscAclEntry 6} 

--xxx.100.20.7.1.7
dcscmscAclPermitOrDeny  OBJECT-TYPE
            SYNTAX      INTEGER 
            {
            permit(1),
            deny(0),
            deltheAcl(2)
            }
            MAX-ACCESS  read-write
            STATUS      current
            DESCRIPTION
                " acl entry permit or deny;0:deny; 1:permit; 2:del this acl"
            ::= { dcscmscAclEntry 7} 
            
--xxx.100.20.8

-- The DCSCM Sc Port binding Table

dcscmscPortbindingTable OBJECT-TYPE
    SYNTAX     SEQUENCE OF DcscmscPortbindingEntry
    MAX-ACCESS not-accessible
    STATUS     current
    DESCRIPTION
           "dcscm destination control multicast, Acl is binded to Port"
    ::= { dcscm 8 }
--xxx.100.20.8.1
dcscmscPortbindingEntry OBJECT-TYPE
    SYNTAX     DcscmscPortbindingEntry
    MAX-ACCESS not-accessible
    STATUS     current
    DESCRIPTION
            "The index of this table is PortName"
    INDEX      { dcscmscPortbindingPortName }
    ::= { dcscmscPortbindingTable 1 }

DcscmscPortbindingEntry
        ::= SEQUENCE
            {
                dcscmscPortbindingPortName           INTEGER,
                dcscmscPortbindingAclNumber          INTEGER
            }
            
--xxx.100.20.8.1.1
dcscmscPortbindingPortName  OBJECT-TYPE
            SYNTAX      INTEGER
            MAX-ACCESS  read-only
            STATUS      current
            DESCRIPTION
                " Dcscm source control multicast,The Port Number of rule"
            ::= { dcscmscPortbindingEntry 1 }  
 
--xxx.100.20.8.1.2
dcscmscPortbindingAclNumber  OBJECT-TYPE
            SYNTAX      INTEGER  (0|5000..5099)
            MAX-ACCESS  read-write
            STATUS      current
            DESCRIPTION
                " Dcscm source control multicast,The Acl number of rule ; 0 means to del the rule binded to port"
            ::= { dcscmscPortbindingEntry 2 } 
                         
--xxx.100.20.9

-- The DCSCM Policy multicast Table

dcscmpcTable OBJECT-TYPE
    SYNTAX     SEQUENCE OF DcscmpcEntry
    MAX-ACCESS not-accessible
    STATUS     current
    DESCRIPTION
           "dcscm policy multicast table"
    ::= { dcscm 9 }
--xxx.100.20.9.1
dcscmpcEntry OBJECT-TYPE
    SYNTAX     DcscmpcEntry
    MAX-ACCESS not-accessible
    STATUS     current
    DESCRIPTION
            "The index of this table is dcscmpcSourceIp,dcscmpcSourceMasklen,dcscmpcDestinationIp,dcscmpcDestinationMasklen"
    INDEX      {dcscmpcSourceIp,dcscmpcSourceMasklen,dcscmpcDestinationIp,dcscmpcDestinationMasklen}
    ::= { dcscmpcTable 1 }

DcscmpcEntry
        ::= SEQUENCE
            {
                dcscmpcSourceIp		          IpAddress,
                dcscmpcSourceMasklen   		   INTEGER,
                dcscmpcDestinationIp        IpAddress,
                dcscmpcDestinationMasklen      INTEGER,
                dcscmpccos                  INTEGER
            }
            
--xxx.100.20.9.1.1
dcscmpcSourceIp  OBJECT-TYPE
            SYNTAX      IpAddress 
            MAX-ACCESS  read-only
            STATUS      current
            DESCRIPTION
                "source ip address of policy multicast "
            ::= { dcscmpcEntry 1}  
      
--xxx.100.20.9.1.2
dcscmpcSourceMasklen  OBJECT-TYPE
            SYNTAX      INTEGER 
            MAX-ACCESS  read-only
            STATUS      current
            DESCRIPTION
                "Mask length of source Ip"
            ::= { dcscmpcEntry 2}        

--xxx.100.20.9.1.3
dcscmpcDestinationIp  OBJECT-TYPE
            SYNTAX      IpAddress 
            MAX-ACCESS  read-only
            STATUS      current
            DESCRIPTION
                "Destination ip address of policy multicast,the destination ip must be a valid multicast group address. "
            ::= { dcscmpcEntry 3}              
            
--xxx.100.20.9.1.4
dcscmpcDestinationMasklen  OBJECT-TYPE
            SYNTAX      INTEGER 
            MAX-ACCESS  read-only
            STATUS      current
            DESCRIPTION
                "Mask length of destination Ip"
            ::= { dcscmpcEntry 4} 

--xxx.100.20.9.1.5
dcscmpccos  OBJECT-TYPE
            SYNTAX      INTEGER (0..8)
            MAX-ACCESS  read-write
            STATUS      current
            DESCRIPTION
                " cos value of policy multicast; between 0 and 7 ;8 means to del the policy"
            ::= { dcscmpcEntry 5} 
            

--xxx.100.21.1 Dcscm6 dc

-- The Dcscm6 dc Enable Table

dcscm6dcEnable OBJECT-TYPE
    SYNTAX     INTEGER
    {
        disable(0),
        enable(1)
    }
    MAX-ACCESS read-write
    STATUS     current
    DESCRIPTION
           "dcscm6 destination control multicast is disable or enable"
    ::= { dcscm6 1 }

--xxx.100.21.2

-- The DCSCM6 dc Acl Table

dcscm6dcAcl                    OBJECT IDENTIFIER ::= { dcscm6 2 }
            
--xxx.100.21.2.1
dcscm6dcAclNumber  OBJECT-TYPE
            SYNTAX      INTEGER (9000..10999)
            MAX-ACCESS  read-write
            STATUS      current
            DESCRIPTION
                "Acl number of Dcscm6 destination control multicast,the range is 9000--10999."
            ::= { dcscm6dcAcl 1 }
            
--xxx.100.21.2.2
dcscm6dcAclSourceIp  OBJECT-TYPE
            SYNTAX      Ipv6Address 
            MAX-ACCESS  read-write
            STATUS      current
            DESCRIPTION
                "Source ip address of acl entry "
            ::= { dcscm6dcAcl 2}  
      
--xxx.100.21.2.3
dcscm6dcAclSourceMask  OBJECT-TYPE
            SYNTAX      INTEGER (1..128) 
            MAX-ACCESS  read-write
            STATUS      current
            DESCRIPTION
                "Source MaskLen of acl entry "
            ::= { dcscm6dcAcl 3}        

--xxx.100.21.2.4
dcscm6dcAclDestinationIp  OBJECT-TYPE
            SYNTAX      Ipv6Address 
            MAX-ACCESS  read-write
            STATUS      current
            DESCRIPTION
                "Destination ip address of acl entry,the destination ip must be a valid multicast group address. "
            ::= { dcscm6dcAcl 4}              
            
--xxx.100.21.2.5
dcscm6dcAclDestinationMask  OBJECT-TYPE
            SYNTAX      INTEGER (8..128)
            MAX-ACCESS  read-write
            STATUS      current
            DESCRIPTION
                "Destination MaskLen of acl entry ,the mask length should meet the request of multicast group address."
            ::= { dcscm6dcAcl 5} 

--xxx.100.21.2.6
dcscm6dcAclPermitOrDeny  OBJECT-TYPE
            SYNTAX      INTEGER 
            {
            permit(1),
            deny(0),
            deltheAcl(2)
            }
            MAX-ACCESS  read-write
            STATUS      current
            DESCRIPTION
                " acl entry permit or deny; 0:deny; 1:permit; 2:del this acl"
            ::= { dcscm6dcAcl 6}    
 
--xxx.100.21.3

-- The DCSCM6 VMac Destination binding Table

dcscm6VMacbindingTable OBJECT-TYPE
    SYNTAX     SEQUENCE OF Dcscm6VMacbindingEntry
    MAX-ACCESS not-accessible
    STATUS     current
    DESCRIPTION
           "dcscm6 destination control multicast, Acl is binded to VMac"
    ::= { dcscm6 3 }
--xxx.100.21.3.1
dcscm6VMacbindingEntry OBJECT-TYPE
    SYNTAX     Dcscm6VMacbindingEntry
    MAX-ACCESS not-accessible
    STATUS     current
    DESCRIPTION
            "The index of this table is Vlanid,MacAddress"
    INDEX      { dcscm6VMacbindingVlanid,dcscm6VMacbindingMacAddr }
    ::= { dcscm6VMacbindingTable 1 }

Dcscm6VMacbindingEntry
        ::= SEQUENCE
            {
                dcscm6VMacbindingVlanid            INTEGER,
                dcscm6VMacbindingMacAddr           MacAddress,
                dcscm6VMacbindingAclNumber         INTEGER
            }
            
--xxx.100.21.3.1.1
dcscm6VMacbindingVlanid  OBJECT-TYPE
            SYNTAX      INTEGER (1..4094)
            MAX-ACCESS  read-only
            STATUS      current
            DESCRIPTION
                " Dcscm6 destination control multicast,The vlanid of rule"
            ::= { dcscm6VMacbindingEntry 1 }  
 
--xxx.100.21.3.1.2
dcscm6VMacbindingMacAddr  OBJECT-TYPE
            SYNTAX      MacAddress 
            MAX-ACCESS  read-only
            STATUS      current
            DESCRIPTION
                " Dcscm6 destination control multicast,The Mac Address of rule"
            ::= { dcscm6VMacbindingEntry 2 }    
            
--xxx.100.21.3.1.3
dcscm6VMacbindingAclNumber  OBJECT-TYPE
            SYNTAX      INTEGER (0|9000..10999)
            MAX-ACCESS  read-write
            STATUS      current
            DESCRIPTION
                " Dcscm6 destination control multicast,The Acl number of rule;0 means del the rule binded to vmac"
            ::= { dcscm6VMacbindingEntry 3 }                                

--xxx.100.21.4

-- The DCSCM6 Sip Destination binding Table

dcscm6SipbindingTable OBJECT-TYPE
    SYNTAX     SEQUENCE OF Dcscm6SipbindingEntry
    MAX-ACCESS not-accessible
    STATUS     current
    DESCRIPTION
           "dcscm6 destination control multicast, Acl is binded to Sip"
    ::= { dcscm6 4 }    
--xxx.100.21.4.1
dcscm6SipbindingEntry OBJECT-TYPE
    SYNTAX     Dcscm6SipbindingEntry
    MAX-ACCESS not-accessible
    STATUS     current
    DESCRIPTION
            "The index of this table is Sourceip,SourceMaskLen "
    INDEX      { dcscm6SipbindingSipAddress,dcscm6SipbindingSipMaskLen }
    ::= { dcscm6SipbindingTable 1 }

Dcscm6SipbindingEntry
        ::= SEQUENCE
            {
                dcscm6SipbindingSipAddress           Ipv6Address,
                dcscm6SipbindingSipMaskLen           INTEGER,
                dcscm6SipbindingAclNumber         INTEGER
            }
            
--xxx.100.21.4.1.1
dcscm6SipbindingSipAddress  OBJECT-TYPE
            SYNTAX      Ipv6Address 
            MAX-ACCESS  read-only
            STATUS      current
            DESCRIPTION
                " Dcscm6 destination control multicast,The Source ip of rule"
            ::= { dcscm6SipbindingEntry 1 }  
 
--xxx.100.21.4.1.2
dcscm6SipbindingSipMaskLen  OBJECT-TYPE
            SYNTAX      INTEGER (1..128)
            MAX-ACCESS  read-only
            STATUS      current
            DESCRIPTION
                " Dcscm6 destination control multicast,The Source ip mask len of rule"
            ::= { dcscm6SipbindingEntry 2 }    
            
--xxx.100.21.4.1.3
dcscm6SipbindingAclNumber  OBJECT-TYPE
            SYNTAX      INTEGER (0|9000..10999)
            MAX-ACCESS  read-write
            STATUS      current
            DESCRIPTION
                " Dcscm6 destination control multicast,The Acl number of rule;0 means del the rule binded to sip"
            ::= { dcscm6SipbindingEntry 3 }
            
--xxx.100.21.5

-- The DCSCM6 Port Destination binding Table

dcscm6dcPortbindingTable OBJECT-TYPE
    SYNTAX     SEQUENCE OF Dcscm6dcPortbindingEntry
    MAX-ACCESS not-accessible
    STATUS     current
    DESCRIPTION
           "dcscm6 destination control multicast, Acl is binded to Port"
    ::= { dcscm6 5 }
--xxx.100.21.5.1
dcscm6dcPortbindingEntry OBJECT-TYPE
    SYNTAX     Dcscm6dcPortbindingEntry
    MAX-ACCESS not-accessible
    STATUS     current
    DESCRIPTION
            "The index of this table is PortName"
    INDEX      { dcscm6dcPortbindingPortName }
    ::= { dcscm6dcPortbindingTable 1 }

Dcscm6dcPortbindingEntry
        ::= SEQUENCE
            {
                dcscm6dcPortbindingPortName           INTEGER,
                dcscm6dcPortbindingAclNumber         INTEGER
            }
            
--xxx.100.21.5.1.1
dcscm6dcPortbindingPortName  OBJECT-TYPE
            SYNTAX      INTEGER
            MAX-ACCESS  read-only
            STATUS      current
            DESCRIPTION
                " Dcscm6 destination control multicast,The Port Number of rule"
            ::= { dcscm6dcPortbindingEntry 1 }  
 
--xxx.100.21.5.1.2
dcscm6dcPortbindingAclNumber  OBJECT-TYPE
            SYNTAX      INTEGER (0|9000..10999)
            MAX-ACCESS  read-write
            STATUS      current
            DESCRIPTION
                " Dcscm6 destination control multicast,The Acl number of rule;0 means del the rule binded to port"
            ::= { dcscm6dcPortbindingEntry 2 }  
            
--xxx.100.21.6 Dcscm6 sc

-- The Dcscm6 sc Enable Table

dcscm6scEnable OBJECT-TYPE
    SYNTAX     INTEGER
    {
        disable(0),
        enable(1)
    }
    MAX-ACCESS read-write
    STATUS     current
    DESCRIPTION
           "dcscm6 source control multicast is disable or enable"
    ::= { dcscm6 6 }

--xxx.100.21.7

-- The DCSCM6 Sc Acl Table

dcscm6scAcl                    OBJECT IDENTIFIER ::= { dcscm6 7 }
            
--xxx.100.21.7.1
dcscm6scAclNumber  OBJECT-TYPE
            SYNTAX      INTEGER (8000..8099)
            MAX-ACCESS  read-write
            STATUS      current
            DESCRIPTION
                "Acl number of Dcscm6 source control multicast.the range is 8000--8099"
            ::= { dcscm6scAcl 1 }
            
--xxx.100.21.7.2
dcscm6scAclSourceIp  OBJECT-TYPE
            SYNTAX      Ipv6Address
            MAX-ACCESS  read-write
            STATUS      current
            DESCRIPTION
                "Source ip address of acl entry "
            ::= { dcscm6scAcl 2}  
      
--xxx.100.21.7.3
dcscm6scAclSourceMask  OBJECT-TYPE
            SYNTAX      INTEGER (1..128)
            MAX-ACCESS  read-write
            STATUS      current
            DESCRIPTION
                "Source MaskLen of acl entry "
            ::= { dcscm6scAcl 3}        

--xxx.100.21.7.4
dcscm6scAclDestinationIp  OBJECT-TYPE
            SYNTAX      Ipv6Address 
            MAX-ACCESS  read-write
            STATUS      current
            DESCRIPTION
                "Destination ip address of acl entry,the destination ip must be a valid multicast group address. "
            ::= { dcscm6scAcl 4}              
            
--xxx.100.21.7.5
dcscm6scAclDestinationMask  OBJECT-TYPE
            SYNTAX      INTEGER (8..128)
            MAX-ACCESS  read-write
            STATUS      current
            DESCRIPTION
                "Destination MaskLen of acl entry ,the mask length should meet the request of multicast group address."
            ::= { dcscm6scAcl 5} 

--xxx.100.21.7.6
dcscm6scAclPermitOrDeny  OBJECT-TYPE
            SYNTAX      INTEGER 
            {
            permit(1),
            deny(0),
            deltheAcl(2)
            }
            MAX-ACCESS  read-write
            STATUS      current
            DESCRIPTION
                " acl entry permit or deny; 0:deny; 1:permit; 2:del this acl"
            ::= { dcscm6scAcl 6} 
            
--xxx.100.21.8

-- The DCSCM6 Sc Port Destination binding Table

dcscm6scPortbindingTable OBJECT-TYPE
    SYNTAX     SEQUENCE OF Dcscm6scPortbindingEntry
    MAX-ACCESS not-accessible
    STATUS     current
    DESCRIPTION
           "dcscm6 destination control multicast, Acl is binded to Port"
    ::= { dcscm6 8 }
--xxx.100.21.8.1
dcscm6scPortbindingEntry OBJECT-TYPE
    SYNTAX     Dcscm6scPortbindingEntry
    MAX-ACCESS not-accessible
    STATUS     current
    DESCRIPTION
            "The index of this table is PortName"
    INDEX      { dcscm6scPortbindingPortName }
    ::= { dcscm6scPortbindingTable 1 }

Dcscm6scPortbindingEntry
        ::= SEQUENCE
            {
                dcscm6scPortbindingPortName           INTEGER,
                dcscm6scPortbindingAclNumber          INTEGER
            }
            
--xxx.100.21.8.1.1
dcscm6scPortbindingPortName  OBJECT-TYPE
            SYNTAX      INTEGER
            MAX-ACCESS  read-only
            STATUS      current
            DESCRIPTION
                " Dcscm6 source control multicast,The Port Number of rule"
            ::= { dcscm6scPortbindingEntry 1 }  
 
--xxx.100.21.8.1.2
dcscm6scPortbindingAclNumber  OBJECT-TYPE
            SYNTAX      INTEGER (0|8000..8099)
            MAX-ACCESS  read-write
            STATUS      current
            DESCRIPTION
                " Dcscm6 source control multicast,The Acl number of rule,0 means to del the rule binded to port"
            ::= { dcscm6scPortbindingEntry 2 } 
                         
--xxx.100.21.9

-- The DCSCM6 Policy multicast Table

dcscm6pcTable OBJECT-TYPE
    SYNTAX     SEQUENCE OF Dcscm6pcEntry
    MAX-ACCESS not-accessible
    STATUS     current
    DESCRIPTION
           "dcscm6 policy multicast table"
    ::= { dcscm6 9 }
--xxx.100.21.9.1
dcscm6pcEntry OBJECT-TYPE
    SYNTAX     Dcscm6pcEntry
    MAX-ACCESS not-accessible
    STATUS     current
    DESCRIPTION
            "The index of this table is dcscm6pcSourceIp,dcscm6pcSourceMask,dcscm6pcDestinationIp,dcscm6pcDestinationMask"
    INDEX      {dcscm6pcSourceIp,dcscm6pcSourceMask,dcscm6pcDestinationIp,dcscm6pcDestinationMask}
    ::= { dcscm6pcTable 1 }

Dcscm6pcEntry
        ::= SEQUENCE
            {
                dcscm6pcSourceIp		         Ipv6Address,
                dcscm6pcSourceMask   		     INTEGER,
                dcscm6pcDestinationIp        Ipv6Address,
                dcscm6pcDestinationMask      INTEGER,
                dcscm6pccos                  INTEGER
            }
            
--xxx.100.21.9.1.1
dcscm6pcSourceIp  OBJECT-TYPE
            SYNTAX      Ipv6Address 
            MAX-ACCESS  read-only
            STATUS      current
            DESCRIPTION
                "source ip address of policy multicast "
            ::= { dcscm6pcEntry 1}  
      
--xxx.100.21.9.1.2
dcscm6pcSourceMask  OBJECT-TYPE
            SYNTAX      INTEGER (1..128)
            MAX-ACCESS  read-only
            STATUS      current
            DESCRIPTION
                "Source MaskLen  of policy multicast "
            ::= { dcscm6pcEntry 2}        

--xxx.100.21.9.1.3
dcscm6pcDestinationIp  OBJECT-TYPE
            SYNTAX      Ipv6Address 
            MAX-ACCESS  read-only
            STATUS      current
            DESCRIPTION
                "Destination ip address of policy multicast "
            ::= { dcscm6pcEntry 3}              
            
--xxx.100.21.9.1.4
dcscm6pcDestinationMask  OBJECT-TYPE
            SYNTAX      INTEGER (8..128)
            MAX-ACCESS  read-only
            STATUS      current
            DESCRIPTION
                "Destination MaskLen of policy multicast "
            ::= { dcscm6pcEntry 4} 

--xxx.100.21.9.1.5
dcscm6pccos  OBJECT-TYPE
            SYNTAX      INTEGER  (0..8)
            MAX-ACCESS  read-write
            STATUS      current
            DESCRIPTION
                " cos value of policy multicast; between 0 and 7 ;8 means to del the policy"
            ::= { dcscm6pcEntry 5}  
            
--********************************************************************************************************
--********************************************************************************************************  

--xxx.100.22.1
clusterv2Base            OBJECT IDENTIFIER ::= { prClusterv2 1 }

--xxx.100.22.1.1
clusterv2BaseKey OBJECT-TYPE
    SYNTAX        OCTET STRING (SIZE (1..16))
    MAX-ACCESS    read-write
    STATUS        current
    DESCRIPTION
            "cluster run switch,set the key word only while the cluster is not running
            and you should set it with set clusterv2BaseRun."
    ::= { clusterv2Base 1 }

--xxx.100.22.1.2
clusterv2BaseVlan OBJECT-TYPE
    SYNTAX        INTEGER (1..4094)
    MAX-ACCESS    read-write
    STATUS        current
    DESCRIPTION
            "cluster run switch,set the Vlan only when the cluster is not running
            and you should set it with set clusterv2BaseRun.
            if get result is 0 that the cluser is not running!"
    ::= { clusterv2Base 2 }

--xxx.100.22.1.3
clusterv2BaseRun OBJECT-TYPE
    SYNTAX       INTEGER {
                           enable(1),
                           disable(0)
                          }
    MAX-ACCESS    read-write
    STATUS        current
    DESCRIPTION
            "cluster run switch,set the key word and vlan id or stop the cluster."
    ::= { clusterv2Base 3 }

--xxx.100.22.1.4
clusterv2BaseRole OBJECT-TYPE
    SYNTAX       INTEGER {
                           candidateDevice(1),
                           memberDevice(2),
                           commanderDevice(3),                                          
                           none(255)
                          }
    MAX-ACCESS    read-only
    STATUS        current
    DESCRIPTION
            "The role of the device. 
            none means cluster device isn't running."
    ::= { clusterv2Base 4 }

--xxx.100.22.1.5
clusterv2BaseVersion OBJECT-TYPE
    SYNTAX      OCTET STRING (SIZE (1..10))
    MAX-ACCESS  read-only
    STATUS      current
    DESCRIPTION
            "version of cluster."
    ::= { clusterv2Base 5 }

--xxx.100.22.1.6
clusterv2BaseMaxNumberOfMembers OBJECT-TYPE
    SYNTAX        INTEGER
    MAX-ACCESS    read-only
    STATUS        current
    DESCRIPTION
            "The maximum number of cluster members allowed in the
             cluster.  The command switch is considered as a cluster
             member also."
    ::= { clusterv2Base 6 }
    
--xxx.100.22.1.7    
clusterv2BaseMaxNumberOfSwitches OBJECT-TYPE
    SYNTAX        INTEGER
    MAX-ACCESS    read-only
    STATUS        current
    DESCRIPTION
            "The maximum number of cluster switches allowed in the
             cluster. The Candidates include commander,candidate and member."
    ::= { clusterv2Base 7 }

--xxx.100.22.2
clusterv2Create          OBJECT IDENTIFIER ::= { prClusterv2 2 }

--xxx.100.22.2.1
clusterv2CreateIPPool OBJECT-TYPE
    SYNTAX    IpAddress
    MAX-ACCESS    read-write
    STATUS    current
    DESCRIPTION
        "ip pool.Valid cluster ip-pool format like as 10.x.x.x,default is 10.254.254.1 .
        if get result is 0 that the cluser is not running!
        set it only on the device is not commander and should set it with set clusterv2CreateCmdrOperate." 
    ::= { clusterv2Create 1}

--xxx.100.22.2.2
clusterv2CreateName OBJECT-TYPE
    SYNTAX      OCTET STRING (SIZE (1..32))
   	MAX-ACCESS    read-write
   	STATUS    current
   	DESCRIPTION
       "create the clustername while create the cluster commander,
        set it only on the device is not commander and should set it with set clusterv2CreateCmdrOperate."
   	::= { clusterv2Create 2}

--xxx.100.22.2.3
clusterv2CreateCmdrOperate OBJECT-TYPE
   	SYNTAX    INTEGER {   			   								
                         	create(1),
                         	destroy(0)
                       }
   	MAX-ACCESS    read-write
   	STATUS    current
   	DESCRIPTION
       "if set create ,operation is to build cluster according to clusterv2CreateClusterIPPool/clusterv2StatusClusterName.
        if set destroy , operation is try to clear the IPPool and the ClusterName.
        set create only on the device is not commander.
        set destroy only on the device is commander."
   	::= { clusterv2Create 3}

--xxx.100.22.3
clusterv2Status          OBJECT IDENTIFIER ::= { prClusterv2 3 }

--xxx.100.22.3.1
clusterv2StatusClusterName OBJECT-TYPE
    SYNTAX        OCTET STRING (SIZE (1..32))
    MAX-ACCESS    read-write
    STATUS        current
    DESCRIPTION
            "The name of the cluster.Set only on the device is not commander.The default is NULL."
    ::= { clusterv2Status 1 }

--xxx.100.22.3.2
clusterv2StatusKeepalive OBJECT-TYPE
    SYNTAX    INTEGER (3..30)
    MAX-ACCESS    read-write
    STATUS    current
    DESCRIPTION
        "cluster keepalive interval(3-30 second).
        if get result is 0 that the cluser is not running!"
    ::= { clusterv2Status 2 }

--xxx.100.22.3.3
clusterv2StatusLoss-count OBJECT-TYPE
    SYNTAX    INTEGER (1..10)
    MAX-ACCESS    read-write
    STATUS    current
    DESCRIPTION
        "cluster the max(1-10) loss-count packet during the keeplive interval.
        if get result is 0 that the cluser is not running!"
    ::= { clusterv2Status 3}

--xxx.100.22.4
clusterv2Commander       OBJECT IDENTIFIER ::= { prClusterv2 4 }

--xxx.100.22.4.1
clusterv2CommanderAutoAddMem OBJECT-TYPE
    SYNTAX       INTEGER {
                           enable(1),
                           disable(0)
                          }
    MAX-ACCESS    read-write
    STATUS        current
    DESCRIPTION
            "auto add mem switch"
    ::= { clusterv2Commander 1 }

--xxx.100.22.4.2
clusterv2MemberCounter OBJECT-TYPE
    SYNTAX        Counter32
    MAX-ACCESS    read-only
    STATUS        current
    DESCRIPTION
            "member number on commander,read only on commander or will return 65535."
    ::= { clusterv2Commander 2 }

--xxx.100.22.4.3
clusterv2MemberTable OBJECT-TYPE
    SYNTAX      SEQUENCE OF Clusterv2MemberEntry
    MAX-ACCESS  not-accessible
    STATUS      current
    DESCRIPTION
            "This table contains one row per cluster member,
            including the command switch,read only on commander."
    ::= { clusterv2Commander 3 }
--xxx.100.22.4.3.1
clusterv2MemberEntry OBJECT-TYPE
    SYNTAX      Clusterv2MemberEntry
    MAX-ACCESS  not-accessible
    STATUS      current
    DESCRIPTION
            "An entry containing cluster management information
            applicable to a particular cluster member."
    INDEX { clusterv2MemberNumber }
    ::= { clusterv2MemberTable 1 }

Clusterv2MemberEntry ::= 
      SEQUENCE {
      				 clusterv2MemberNumber                  INTEGER,
               clusterv2MemberIpAddress               IpAddress,               
               clusterv2MemberMacAddress              MacAddress,
               clusterv2MemberOperStatus              INTEGER,
               clusterv2MemberHostName		    				OCTET STRING,
               clusterv2MemberDeviceType		    			OCTET STRING
      }

--xxx.100.22.4.3.1.1
clusterv2MemberNumber OBJECT-TYPE
    SYNTAX      INTEGER
    MAX-ACCESS  read-only
    STATUS      current
    DESCRIPTION
            "An arbitrary value which uniquely identifies the 
             cluster member switch number. It ranges from 1 to
             clusterv2StatusMaxNumberOfMembers,read only on commander."
    ::= { clusterv2MemberEntry 1 }
    
--xxx.100.22.4.3.1.2
clusterv2MemberIpAddress OBJECT-TYPE
    SYNTAX      IpAddress
    MAX-ACCESS  read-only
    STATUS      current
    DESCRIPTION
            "The management ip address of the member device."
    ::= { clusterv2MemberEntry 2 }

--xxx.100.22.4.3.1.3
clusterv2MemberOperStatus OBJECT-TYPE
    SYNTAX      INTEGER {
                           notMember(1),
    											 inactiveMember(2),
    											 memberTobe(3),
    											 activeMember(4)
                        }
    MAX-ACCESS  read-only
    STATUS      current
    DESCRIPTION
            "The status of cluster management connectivity between
             the command switch and a cluster member. Cluster management
             connectivity is determined by the exchange of cluster
             management messages between the command switch and a
             cluster member."
    ::= { clusterv2MemberEntry 3 }

--xxx.100.22.4.3.1.4
clusterv2MemberMacAddress OBJECT-TYPE
    SYNTAX      MacAddress 
    MAX-ACCESS  read-only
    STATUS      current
    DESCRIPTION
            "The management MAC address of the member device."
    ::= { clusterv2MemberEntry 4 }

--xxx.100.22.4.3.1.5 
clusterv2MemberHostName OBJECT-TYPE
    SYNTAX        OCTET STRING (SIZE (1..32))
    MAX-ACCESS    read-only
    STATUS        current
    DESCRIPTION
            ""
    ::= { clusterv2MemberEntry 5 }

--xxx.100.22.4.3.1.6
clusterv2MemberDeviceType OBJECT-TYPE
    SYNTAX        OCTET STRING (SIZE (1..32))
    MAX-ACCESS    read-only
    STATUS        current
    DESCRIPTION
            "deviceType such as 5526S, 2008A etc"
    ::= { clusterv2MemberEntry 6 }   
    
--The Cluster Candidate Table
--xxx.100.22.4.4
clusterv2CandidateCounter OBJECT-TYPE
    SYNTAX        Counter32
    MAX-ACCESS    read-only
    STATUS        current
    DESCRIPTION
            "candidate number on commander,read only on commander or will return 65535."
    ::= { clusterv2Commander 4 }
--xxx.100.22.4.5
clusterv2CandidateTable OBJECT-TYPE
    SYNTAX      SEQUENCE OF Clusterv2CandidateEntry
    MAX-ACCESS  not-accessible
    STATUS      current
    DESCRIPTION
            "This table contains one row per cluster candidate,
             A cluster candidate is a device that is currently
             eligible to be added to the cluster of a command
             switch.  A device is eligible if it satisfies the
             following conditions:
             1. It start the cluster func.
             2. It is in a same L2 LAN with commander switch
       
             The entries in this table and the entries in 
             clusterMemberTable are mutually exclusive at all
             times.  That is, any device that is a cluster
             member never shows up in the clusterCandidateTable
             or is never a candidate at the same time .  Also, any 
             candidate that shows up in clusterCandidateTable should not
             appear in clusterMemberTable."
    ::= { clusterv2Commander 5 }

--xxx.100.22.4.5.1
clusterv2CandidateEntry       OBJECT-TYPE
    SYNTAX      Clusterv2CandidateEntry
    MAX-ACCESS  not-accessible
    STATUS      current
    DESCRIPTION
            "An entry pertaining to a single candidate device."
    INDEX { clusterv2CandidateId }
    ::= { clusterv2CandidateTable 1 }

Clusterv2CandidateEntry ::= SEQUENCE {
      clusterv2CandidateId    INTEGER,
      clusterv2CandidateMacAddress    MacAddress,
      clusterv2CandidateHostName			OCTET STRING,
      clusterv2CandidateDeviceType		OCTET STRING
}

--xxx.100.22.4.5.1.1
clusterv2CandidateId OBJECT-TYPE
    SYNTAX      INTEGER
    MAX-ACCESS  read-only
    STATUS      current
    DESCRIPTION
            "The candidate id."
    ::= { clusterv2CandidateEntry 1 }


--xxx.100.22.4.5.1.2
clusterv2CandidateMacAddress OBJECT-TYPE
    SYNTAX      MacAddress 
    MAX-ACCESS  read-only
    STATUS      current
    DESCRIPTION
            "The MAC address of a device qualified to
             to be a cluster member of the command switch 
             cluster."
    ::= { clusterv2CandidateEntry 2 }    

--xxx.100.22.4.5.1.3
clusterv2CandidateHostName OBJECT-TYPE
    SYNTAX        OCTET STRING (SIZE (1..32))
    MAX-ACCESS    read-only
    STATUS        current
    DESCRIPTION
            ""
    ::= { clusterv2CandidateEntry 3 }

--xxx.100.22.4.5.1.4
clusterv2CandidateDeviceType OBJECT-TYPE
    SYNTAX        OCTET STRING (SIZE (1..32))
    MAX-ACCESS    read-only
    STATUS        current
    DESCRIPTION
            ""
    ::= { clusterv2CandidateEntry 4 }
    
    
--xxx.100.22.4.6
clusterv2RebootMem OBJECT-TYPE
    SYNTAX        OCTET STRING (SIZE (1..30))
   	MAX-ACCESS    read-write
   	STATUS    current
   	DESCRIPTION
       "Operation is to reboot the specified member.you can select more member one time,
       the value connected with '-' or ';',the string len is 1-30 .set only on commander."
   	::= { clusterv2Commander 6}
   	
--********************************************************************************************************
--******************************************************************************************************** 
--xxx.100.23 Dns group

--xxx.100.23.1
dnsEnable OBJECT-TYPE
    SYNTAX  INTEGER{
                disable(0),
                enable(1)
            }
            MAX-ACCESS  read-write
            STATUS  current
            DESCRIPTION
                "Enable or disable dns dynamic domain resolving."
            ::= {dns 1 }           
    
--xxx.100.23.2

-- The DNS Server List Table

dnsServerTable OBJECT-TYPE
    SYNTAX     SEQUENCE OF DnsServerEntry
    MAX-ACCESS not-accessible
    STATUS     current
    DESCRIPTION
           "The dns server list table which consists of a sequence of 'dnsServerEntry' items which describe
           the configured dns server IP information."
    ::= { dns 2 }
    
--xxx.100.23.2.1
dnsServerEntry OBJECT-TYPE
    SYNTAX     DnsServerEntry
    MAX-ACCESS not-accessible
    STATUS     current
    DESCRIPTION
            "An entry in the dnsServerTable containing the dns server IP."
    INDEX      { dnsServerInetAddrType,dnsServerIpAddr }
    ::= {dnsServerTable 1 }

DnsServerEntry
        ::= SEQUENCE
            {
                dnsServerInetAddrType       InetAddressType,
                dnsServerIpAddr		          InetAddress,
                dnsServerPriority	          INTEGER,
                dnsServerStatus	            INTEGER
            }
            
--xxx.100.23.2.1.1
dnsServerInetAddrType   OBJECT-TYPE
            SYNTAX      InetAddressType 
            MAX-ACCESS  not-accessible
            STATUS      current
            DESCRIPTION
                "The IP address type of dnsServerEntry. This value applies to dnsServerIpAddr."
            ::= { dnsServerEntry 1 }
      
--xxx.100.23.2.1.2
dnsServerIpAddr  OBJECT-TYPE
            SYNTAX      InetAddress 
            MAX-ACCESS  read-only
            STATUS      current
            DESCRIPTION
                "The dns server IP address with 'dnsServerInetAddrType' to indicate the IP address type(IPv4 or IPv6)."
            ::= { dnsServerEntry 2}    
            
--xxx.100.23.2.1.3           
dnsServerPriority OBJECT-TYPE
            SYNTAX  INTEGER(0..255)
            MAX-ACCESS  read-create
            STATUS  current
            DESCRIPTION
                "Current Priority of the dns server."
            ::= { dnsServerEntry  3 }            

--xxx.100.23.2.1.4           
dnsServerStatus OBJECT-TYPE
            SYNTAX  INTEGER
            	    {
            	    	createAndGo(0),
               		  active(1),
               		  destroy(2)
            	    }
            MAX-ACCESS  read-create
            STATUS  current
            DESCRIPTION
                "Current state of the dns server."
            ::= { dnsServerEntry  4 }                                                      
            
--xxx.100.23.3

-- The DNS Domain Suffix Table

dnsDomainSuffixTable OBJECT-TYPE
    SYNTAX     SEQUENCE OF DnsDomainSuffixEntry
    MAX-ACCESS not-accessible
    STATUS     current
    DESCRIPTION
           "The dns domain suffix table which consists of a sequence of 'dnsDomainSuffixEntry' items which describe
           the configured dns domain suffix information."
    ::= { dns 3 }
    
--xxx.100.23.3.1
dnsDomainSuffixEntry OBJECT-TYPE
    SYNTAX     DnsDomainSuffixEntry
    MAX-ACCESS not-accessible
    STATUS     current
    DESCRIPTION
            "An entry in the dnsDomainSuffixTable containing the dns domain suffix."
    INDEX      { dnsDomainSuffix }
    ::= { dnsDomainSuffixTable 1 }

DnsDomainSuffixEntry
        ::= SEQUENCE
            {
                dnsDomainSuffix               	DisplayString,
                dnsDomainSuffixStatus	          INTEGER
            }
            
--xxx.100.23.3.1.1
dnsDomainSuffix  OBJECT-TYPE
            SYNTAX      DisplayString 
            MAX-ACCESS  read-only
            STATUS      current
            DESCRIPTION
                "The dns domain suffix(e.g. commpany.com)."
            ::= { dnsDomainSuffixEntry 1 }

--xxx.100.23.3.1.2          
dnsDomainSuffixStatus OBJECT-TYPE
            SYNTAX  INTEGER
            	    {
            	    	createAndGo(0),
               		  active(1),
               		  destroy(2)
            	    }
            MAX-ACCESS  read-create
            STATUS  current
            DESCRIPTION
                "Current state of the dns domain suffix."
            ::= { dnsDomainSuffixEntry  2 }            
      
--xxx.100.23.4

-- The DNS Dynamic Host Table

dnsDynHostTable OBJECT-TYPE
    SYNTAX     SEQUENCE OF DnsDynHostEntry
    MAX-ACCESS not-accessible
    STATUS     current
    DESCRIPTION
           "The dns dynamic host table which consists of a sequence of 'dnsDynHostEntry' items which describe
           the resolved dns dynamic host information."
    ::= { dns 4 }
    
--xxx.100.23.4.1
dnsDynHostEntry OBJECT-TYPE
    SYNTAX     DnsDynHostEntry
    MAX-ACCESS not-accessible
    STATUS     current
    DESCRIPTION
            "An entry in the dnsDynHostTable containing the dns dynamic host information."
    INDEX      { dnsDynHostIndex }
    ::= { dnsDynHostTable 1 }

   
DnsDynHostEntry
        ::= SEQUENCE
            {   
                dnsDynHostIndex                  INTEGER,
                dnsDynHostName	                 DisplayString,
                dnsDynHostIpAddr					       InetAddress,   
                dnsDynHostTtl                    INTEGER 	
            }
            
--xxx.100.23.4.1.1
dnsDynHostIndex  OBJECT-TYPE
    SYNTAX     INTEGER
    MAX-ACCESS not-accessible
    STATUS     current
    DESCRIPTION
        "Index of position in the cache "
    ::= { dnsDynHostEntry 1 }
      

--xxx.100.23.4.1.2
dnsDynHostName  OBJECT-TYPE
            SYNTAX      DisplayString 
            MAX-ACCESS  read-only
            STATUS      current
            DESCRIPTION
                "The dns dynamic host name(e.g. www.sina.com.cn)."
            ::= { dnsDynHostEntry 2 }

--xxx.100.23.4.1.3
dnsDynHostIpAddr  OBJECT-TYPE
            SYNTAX      InetAddress 
            MAX-ACCESS  read-only
            STATUS      current
            DESCRIPTION
                "The dns dynamic host's IP address with 'dnsDynHostInetAddrType' to indicate the IP address type(IPv4 or IPv6)."
            ::= { dnsDynHostEntry 3} 
            
--xxx.100.23.4.1.4
dnsDynHostTtl  OBJECT-TYPE
            SYNTAX      INTEGER 
            MAX-ACCESS  read-only
            STATUS      current
            DESCRIPTION
                "The dns dynamic host's living time(seconds)."
            ::= { dnsDynHostEntry 4}    	

--
-- Textual Conventions
--

NtpStratum ::= TEXTUAL-CONVENTION
    DISPLAY-HINT "d"
    STATUS      current
    DESCRIPTION
        "The NTP stratum, with 16 representing no stratum."
    SYNTAX      Unsigned32 (1..16)

NtpDateTime ::= TEXTUAL-CONVENTION
    DISPLAY-HINT "4d:4d:4d.4d"
    STATUS      current
    DESCRIPTION
        "NTP date/time on the device, in 128-bit
         NTP date format. Ref: draft-ietf-ntp-ntpv4-proto-06,
         section 6:
          It includes a 64-bit signed seconds field
          spanning 584 billion years and a 64-bit fraction
          field resolving .05 attosecond (i.e. 0.5e-18).
          For convenience in mapping between formats, the
          seconds field is divided into a 32-bit era field
          and a 32-bit timestamp field.

         If time is not syncronized this field shall be a
         zero-length string.

         This TC is not to be used for objects that are used
         to set the time of the node querying this object.
         NTP should be used for this--or at least SNTP."
    SYNTAX      OCTET STRING (SIZE (0 | 16))

--
-- Section 1: General NTP Entity information objects
--            (relatively static information)
--

ntpEntSoftwareName OBJECT-TYPE
    SYNTAX      DisplayString
    MAX-ACCESS  read-only
    STATUS      current
    DESCRIPTION
        "The product name of the installed NTP version."
    ::= { ntpEntInfo  1 }

ntpEntSoftwareVersion OBJECT-TYPE
    SYNTAX      DisplayString
    MAX-ACCESS  read-only
    STATUS      current
    DESCRIPTION
        "The software version of the installed NTP implementation."
    ::= { ntpEntInfo  2 }

ntpEntSoftwareVendor OBJECT-TYPE
    SYNTAX      DisplayString
    MAX-ACCESS  read-only
    STATUS      current
    DESCRIPTION
        "The vendor/author of the installed NTP version."
    ::= { ntpEntInfo  4 }

ntpEntSystemType OBJECT-TYPE
    SYNTAX      DisplayString
    MAX-ACCESS  read-only
    STATUS      current
    DESCRIPTION
        "General hardware/os platform information."
    ::= { ntpEntInfo  5 }

ntpEntTimeResolution OBJECT-TYPE
    SYNTAX      DisplayString
    MAX-ACCESS  read-only
    STATUS      current
    DESCRIPTION
        "A string describing the time resolution of the running NTP
         implementation."
    ::= { ntpEntInfo  6 }

ntpEntTimePrecision OBJECT-TYPE
    SYNTAX      Integer32
    MAX-ACCESS  read-only
    STATUS      current
    DESCRIPTION
        "The entity's precision in integer format."
    ::= { ntpEntInfo  9 }

--
-- Section 2: Current NTP status (dynamic information)
--

ntpEntStatusCurrentMode OBJECT-TYPE
    SYNTAX      DisplayString
    MAX-ACCESS  read-only
    STATUS      current
    DESCRIPTION
        "The actual mode of NTP as a string"
    ::= { ntpEntStatus 1 }

ntpEntStatusCurrentModeVal OBJECT-TYPE
    SYNTAX      INTEGER {
                            notRunning(1),
                            notSynchronized(2),
                            noneConfigured(3),
                            syncToLocal(4),
                            syncToRefclock(5),
                            syncToRemoteServer(6),
                            unknown(99)
                        }
    MAX-ACCESS  read-only
    STATUS      current
    DESCRIPTION
        "The current mode of the NTP as integer value."
    DEFVAL { 99 }
    ::= { ntpEntStatus 2 }

ntpEntStatusStratum OBJECT-TYPE
    SYNTAX      NtpStratum
    MAX-ACCESS  read-only
    STATUS      current
    DESCRIPTION
        "The NTP entity's own stratum value."
    DEFVAL { 16 }
    ::= { ntpEntStatus 3 }

ntpEntStatusActiveRefSourceId OBJECT-TYPE
    SYNTAX      Unsigned32 (0..4294967295)
    MAX-ACCESS  read-only
    STATUS      current
    DESCRIPTION
        "The association ID of the current syspeer."
    DEFVAL { 0 }
    ::= { ntpEntStatus 4 }

ntpEntStatusActiveRefSourceName OBJECT-TYPE
    SYNTAX      DisplayString
    MAX-ACCESS  read-only
    STATUS      current
    DESCRIPTION
        "The hostname/descriptive name of the current reference source
         selected as syspeer."
    ::= { ntpEntStatus 5 }

ntpEntStatusNumberOfRefSources OBJECT-TYPE
    SYNTAX      Unsigned32 (0..99)
    MAX-ACCESS  read-only
    STATUS      current
    DESCRIPTION
        "The number of reference sources configured for NTP."
    DEFVAL { 0 }
    ::= { ntpEntStatus 7 }

ntpEntStatusDateTime OBJECT-TYPE
    SYNTAX      NtpDateTime
    MAX-ACCESS  read-only
    STATUS      current
    DESCRIPTION
        "The current NTP date/time on the device, in 128-bit
         NTP date format. Ref: draft-ietf-ntp-ntpv4-proto-06,
         section 6:
          It includes a 64-bit signed seconds field
          spanning 584 billion years and a 64-bit fraction
          field resolving .05 attosecond (i.e. 0.5e-18).
          For convenience in mapping between formats, the
          seconds field is divided into a 32-bit era field
          and a 32-bit timestamp field.

         If time is not syncronized this field shall be a
         zero-length string.

         This object can be used to timestamp events on this
         node and allow a management station to coorelate
         different time objects. For example, a management
         station could query this object and sysUpTime in
         the same operation to be able to relate sysUpTime
         to NTP time.

         This object is not to be used to set the time of
         the node querying this object. NTP should be used
         for this--or at least SNTP."
    ::= { ntpEntStatus 10 }

ntpEntStatusInPkts OBJECT-TYPE
    SYNTAX      Counter32
    MAX-ACCESS  read-only
    STATUS      current
    DESCRIPTION
        "The total number of NTP messages delivered to the
         NTP entity from the transport service."
    ::= { ntpEntStatus 13 }

ntpEntStatusOutPkts OBJECT-TYPE
    SYNTAX      Counter32
    MAX-ACCESS  read-only
    STATUS      current
    DESCRIPTION
        "The total number of NTP messages delivered to the
         transport service by this NTP entity."
    ::= { ntpEntStatus 14 }

ntpEntStatusBadVersion OBJECT-TYPE
    SYNTAX      Counter32
    MAX-ACCESS  read-only
    STATUS      current
    DESCRIPTION
        "The total number of NTP messages which were delivered
         to this NTP entity and were for an unsupported NTP
         version."
    ::= { ntpEntStatus 15 }

ntpEntStatusProtocolError OBJECT-TYPE
    SYNTAX      Counter32
    MAX-ACCESS  read-only
    STATUS      current
    DESCRIPTION
        "The total number of NTP messages which were delivered
         to this NTP entity and this entity was not able to
         process due to an NTP protocol error."
    ::= { ntpEntStatus 16 }



--
-- Conformance/Compliance statements
--

ntpEntConformance OBJECT IDENTIFIER ::= { ntpSnmpMIB 6 }

ntpEntCompliances OBJECT IDENTIFIER ::= { ntpEntConformance 1 }
ntpEntGroups      OBJECT IDENTIFIER ::= { ntpEntConformance 2 }

ntpEntNTPCompliance MODULE-COMPLIANCE
    STATUS      current
    DESCRIPTION
        "The compliance statement for SNMP entities which use NTP and
         implement the NTP MIB"
    MODULE  -- this module
        MANDATORY-GROUPS {
                           ntpEntObjectsGroup1,
                           ntpEntObjectsGroup2
--                           ntpEntNotifPrefixGroup
        }
        ::= { ntpEntCompliances 1 }

ntpEntSNTPCompliance MODULE-COMPLIANCE
    STATUS      current
    DESCRIPTION
        "The compliance statement for SNMP entities which use SNTP and
         implement the NTP MIB"
    MODULE  -- this module
        MANDATORY-GROUPS {
                           ntpEntObjectsGroup1
        }
        ::= { ntpEntCompliances 2 }

ntpEntObjectsGroup1 OBJECT-GROUP
    OBJECTS {
              ntpEntSoftwareName,
              ntpEntSoftwareVersion,
--              ntpEntSoftwareVersionVal,
              ntpEntSoftwareVendor,
              ntpEntSystemType,
--              ntpEntStatusEntityUptime,
              ntpEntStatusDateTime
--              ntpAssocName,
--              ntpAssocRefId,
--              ntpAssocAddressType,
--              ntpAssocAddress
    }
    STATUS      current
    DESCRIPTION
        "A collection of objects for the NTP MIB that all NTP
         or SNTP entities should implement."
    ::= { ntpEntGroups 1 }

ntpEntObjectsGroup2 OBJECT-GROUP
    OBJECTS {
              ntpEntTimeResolution,
--              ntpEntTimeResolutionVal,
              ntpEntTimePrecision,
--              ntpEntTimePrecisionVal,
--              ntpEntTimeDistance,
              ntpEntStatusCurrentMode,
              ntpEntStatusCurrentModeVal,
              ntpEntStatusStratum,
              ntpEntStatusActiveRefSourceId,
              ntpEntStatusActiveRefSourceName,
--              ntpEntStatusActiveOffset,
              ntpEntStatusNumberOfRefSources,
--              ntpEntStatusDispersion,
--              ntpEntStatusLeapSecond,
--              ntpEntStatusLeapSecDirection,
              ntpEntStatusInPkts,
              ntpEntStatusOutPkts,
              ntpEntStatusBadVersion,
              ntpEntStatusProtocolError
--              ntpEntStatusNotifications,
--              ntpAssocOffset,
--              ntpAssocStratum,
--              ntpAssocStatusJitter,
--              ntpAssocStatusDelay,
--              ntpAssocStatusDispersion,
--              ntpAssocStatInPkts,
--              ntpAssocStatOutPkts,
--              ntpAssocStatProtocolError,
--              ntpEntHeartbeatInterval,
--              ntpEntNotifBits,
--              ntpEntNotifMessage
    }
    STATUS      current
    DESCRIPTION
        "A collection of objects for the NTP MIB that are optional
         for NTP or SNTP entities to implement."
    ::= { ntpEntGroups 2 }

--ntpEntNotifPrefixGroup NOTIFICATION-GROUP
--    NOTIFICATIONS {
--                    ntpEntNotifModeChange,
--                    ntpEntNotifStratumChange,
--                    ntpEntNotifSyspeerChanged,
--                    ntpEntNotifAddAssociation,
--                    ntpEntNotifRemoveAssociation,
--                    ntpEntNotifConfigChanged,
--                    ntpEntNotifLeapSecondAnnounced,
--                    ntpEntNotifHeartbeat
--    }
--    STATUS      current
--    DESCRIPTION
--        "A collection of notifications for the NTP MIB"
--    ::= { ntpEntGroups 3 }
 
--********************************************************************************************************
--********************************************************************************************************              

-- (xxx.100.26)   priPoeConfig group
  		    
--xxx.100.26.1
poeSystemEnable OBJECT-TYPE
    SYNTAX  INTEGER
	    {
		         	enable (1), 
		         	disable (0)
	    }  
    MAX-ACCESS  read-write
    STATUS  current
    DESCRIPTION
        " The power inline global switch. Enable expresses it is turned on, while disable indicates that off."
    ::= { priPoeConfig   1 }
    
--xxx.100.26.2
poeMaxPower OBJECT-TYPE
    SYNTAX  INTEGER (37..776) 
    MAX-ACCESS  read-write
    STATUS  current
    DESCRIPTION
        " The power inline global available power whitch cannot be exceeded by the total power of all PDs."
    ::= { priPoeConfig   2 } 
    
--xxx.100.26.3
poePoliceEnable OBJECT-TYPE
    SYNTAX  INTEGER
	    {
		         	enable (1), 
		         	disable (0)
	    }  
    MAX-ACCESS  read-write
    STATUS  current
    DESCRIPTION
        " The power inline power mamagement switch. Enable expresses it is in priority-policy mode, while disable indicates that in first-in-first-get mode."
    ::= { priPoeConfig   3 }  
    
--xxx.100.26.4
poeLegacyEnable OBJECT-TYPE
    SYNTAX  INTEGER
	    {
		         	enable (1), 
		         	disable (0)
	    }  
    MAX-ACCESS  read-write
    STATUS  current
    DESCRIPTION
        " The power inline nonstandard PD detect switch. Enable expresses nonstandard PD can be detected, while disable indicates that cannot be detected."
    ::= { priPoeConfig   4 } 
    
--xxx.100.26.5
poeDisconnect OBJECT-TYPE
    SYNTAX  INTEGER
	    {
		         	ac  (0),
		         	dc  (1)		         	
	    }  
    MAX-ACCESS  read-only
    STATUS  current
    DESCRIPTION
        " The power inline disconnection mode."
    ::= { priPoeConfig  5 }   
    
--xxx.100.26.6
poeCurrentPower OBJECT-TYPE
    SYNTAX  INTEGER
    MAX-ACCESS  read-only
    STATUS  current
    DESCRIPTION
        " The power inline current export power. It is a real time value."
    ::= { priPoeConfig   6 } 
    
--xxx.100.26.7
poePortMode OBJECT-TYPE
        SYNTAX      INTEGER
 	    {
                               spare (1), 
                               signal (0)
	    }        
        MAX-ACCESS  read-only
        STATUS      current
        DESCRIPTION 
        " The power inline power supply mode."
        ::= { priPoeConfig 7 }        
    
--xxx.100.26.8
poeSoftwareVersion OBJECT-TYPE
    SYNTAX  DisplayString (SIZE(1..32))
    MAX-ACCESS  read-only
    STATUS  current
    DESCRIPTION
        " The power inline software version."
    ::= { priPoeConfig   8 }  
    
--xxx.100.26.9
poeHardwareVersion OBJECT-TYPE
    SYNTAX  DisplayString (SIZE(1..32))
    MAX-ACCESS  read-only
    STATUS  current
    DESCRIPTION
        " The power inline hardware version."
    ::= { priPoeConfig   9 }
                                  
--xxx.100.26.10
    poePortConfigTable OBJECT-TYPE
        SYNTAX  SEQUENCE OF PoePortConfigEntry
        MAX-ACCESS  not-accessible
        STATUS  current
        DESCRIPTION
            " The power inline port configuration table"
        ::= { priPoeConfig 10 }
        
--xxx.100.26.10.1
    poePortConfigEntry OBJECT-TYPE
        SYNTAX  PoePortConfigEntry
        MAX-ACCESS  not-accessible
        STATUS  current
        DESCRIPTION
            " The power inline configuration in port."
        INDEX   { portIndex }
        ::= { poePortConfigTable 1 }        

    PoePortConfigEntry
        ::= SEQUENCE
            {
                poePortIndex               INTEGER,
                poePortStatus              INTEGER,
                poePortPriority	           INTEGER,
                poePortMaxPower	           INTEGER,  
                poePortCurrentPower        INTEGER,
                poePortCurrentCurrent	   INTEGER,
                poePortCurrentVoltage      INTEGER,
                poePortPdStatus		   INTEGER,
                poePortPdClass		   INTEGER
            }
            
--xxx.100.26.10.1.1
poePortIndex OBJECT-TYPE
        SYNTAX      INTEGER
        MAX-ACCESS  not-accessible
        STATUS      current
        DESCRIPTION 
            "The power inline port index."
        ::= { poePortConfigEntry 1 }	
        
--xxx.100.26.10.1.2
poePortStatus OBJECT-TYPE
        SYNTAX      INTEGER
 	    {		         	
		         	disable (0),
		         	enableAuto (1), 
		         	enableStatic (2)
	    }        
        MAX-ACCESS  read-write
        STATUS      current
        DESCRIPTION 
        " The power inline port switch. Enable expresses it is turned on, while disable indicates that off.enableAuto(1) turn on the 
        auto-mode,enableStatic(2) turn on the force-mode."
        ::= { poePortConfigEntry 2 } 
        
--xxx.100.26.10.1.3
poePortPriority OBJECT-TYPE
        SYNTAX      INTEGER
 	    {
                               critical (0), 
                               high (1), 
                               low (2)
	    }        
        MAX-ACCESS  read-write
        STATUS      current
        DESCRIPTION 
        " The power inline port priority."
        ::= { poePortConfigEntry 3 }  
        
--xxx.100.26.10.1.4
poePortMaxPower OBJECT-TYPE
        SYNTAX      INTEGER (1..31000)       
        MAX-ACCESS  read-write
        STATUS      current
        DESCRIPTION 
        " The power inline port available power whitch cannot be exceeded by the connected PD."
        ::= { poePortConfigEntry 4 } 
        
--xxx.100.26.10.1.5
poePortCurrentPower OBJECT-TYPE
        SYNTAX      INTEGER        
        MAX-ACCESS  read-only
        STATUS      current
        DESCRIPTION 
        " The power inline port used power. It is a real time value."
        ::= { poePortConfigEntry 5 }    
        
--xxx.100.26.10.1.6
poePortCurrentCurrent OBJECT-TYPE
        SYNTAX      INTEGER        
        MAX-ACCESS  read-only
        STATUS      current
        DESCRIPTION 
        " The power inline port export current. It is a real time value."
        ::= { poePortConfigEntry 6 }  
        
--xxx.100.26.10.1.7
poePortCurrentVoltage OBJECT-TYPE
        SYNTAX      INTEGER        
        MAX-ACCESS  read-only
        STATUS      current
        DESCRIPTION 
        " The power inline port export voltage. It is a real time value."
        ::= { poePortConfigEntry 7 }
        
--xxx.100.26.10.1.8
poePortPdStatus OBJECT-TYPE
        SYNTAX      INTEGER
        {
               on(1), 
               off(2),
               faulty(3),
               deny(4),
               force(5)
        }        
        MAX-ACCESS  read-only
        STATUS      current
        DESCRIPTION 
        " The power inline detect status. on(1):PD is connected and natural powered, off(2):PD is not connected,
        faulty(3):error, deny(4):power is low or high, force(5):force power."
        ::= { poePortConfigEntry 8 } 
        
--xxx.100.26.10.1.9
poePortPdClass OBJECT-TYPE
        SYNTAX      INTEGER        
        MAX-ACCESS  read-only
        STATUS      current
        DESCRIPTION 
        " The connected PD class of power inline"
        ::= { poePortConfigEntry 9 }   
--xxx.100.26.11
poeHighInrushEnable OBJECT-TYPE
    SYNTAX  INTEGER
	    {
		         	enable (0), 
		         	disable (1)
	    }  
    MAX-ACCESS  read-write
    STATUS  current
    DESCRIPTION
        " The power inline high-inrush switch. Enable expresses it is turned on, while disable indicates that off."
    ::= { priPoeConfig   11 }                                                           	                                                                  	             
--********************************************************************************************************
--********************************************************************************************************              

-- (xxx.100.27)   priQos2 group

--xxx.100.27.1
    qos2         	    OBJECT IDENTIFIER ::= { priQos2 1 } 
--********************************************************************************************************
--xxx.100.27.1.1
    qos2MapCostoIntp         	    OBJECT IDENTIFIER ::= { qos2 1 } 
    
--xxx.100.27.1.1.1
        qos2MapCostoIntp1 OBJECT-TYPE
            SYNTAX  INTEGER
            MAX-ACCESS  read-create
            STATUS  current
            DESCRIPTION
                "COS to IntPrio map,IntPrio1<0-7>."
            ::= { qos2MapCostoIntp  1 }

--xxx.100.27.1.1.2
	    qos2MapCostoIntp2 OBJECT-TYPE
	        SYNTAX  INTEGER
	        MAX-ACCESS  read-create
	        STATUS  current
	        DESCRIPTION
	            "COS to IntPrio map,IntPrio2<0-7>."
	        ::= { qos2MapCostoIntp  2 }

--xxx.100.27.1.1.3
	    qos2MapCostoIntp3 OBJECT-TYPE
	        SYNTAX  INTEGER
	        MAX-ACCESS  read-create
	        STATUS  current
	        DESCRIPTION
	            "COS to IntPrio map,IntPrio1<0-7>."
	        ::= { qos2MapCostoIntp  3 }

--xxx.100.27.1.1.4
	    qos2MapCostoIntp4 OBJECT-TYPE
	        SYNTAX  INTEGER
	        MAX-ACCESS  read-create
	        STATUS  current
	        DESCRIPTION
	            "COS to IntPrio map,IntPrio1<0-7>."
	        ::= { qos2MapCostoIntp  4 }

--xxx.100.27.1.1.5
	    qos2MapCostoIntp5 OBJECT-TYPE
	        SYNTAX  INTEGER
	        MAX-ACCESS  read-create
	        STATUS  current
	        DESCRIPTION
	            "COS to IntPrio map,IntPrio1<0-7>."
	        ::= { qos2MapCostoIntp  5 }

--xxx.100.27.1.1.6      
	    qos2MapCostoIntp6 OBJECT-TYPE
	        SYNTAX  INTEGER
	        MAX-ACCESS  read-create
	        STATUS  current
	        DESCRIPTION
	            "COS to IntPrio map,IntPrio1<0-7>."
	        ::= { qos2MapCostoIntp  6 }

--xxx.100.27.1.1.7        
	    qos2MapCostoIntp7 OBJECT-TYPE
	        SYNTAX  INTEGER
	        MAX-ACCESS  read-create
	        STATUS  current
	        DESCRIPTION
	            "COS to IntPrio map,IntPrio1<0-7>."
	        ::= { qos2MapCostoIntp  7 }

--xxx.100.27.1.1.8     
	    qos2MapCostoIntp8 OBJECT-TYPE
	        SYNTAX  INTEGER
	        MAX-ACCESS  read-create
	        STATUS  current
	        DESCRIPTION
	            "COS to IntPrio map,IntPrio1<0-7>."
	        ::= { qos2MapCostoIntp  8 }
                              
--xxx.100.27.1.1.9
        qos2MapCostoIntpStatus OBJECT-TYPE
            SYNTAX  INTEGER
            	    {
               		active(1),
               		destroy(2)
            	    }
            MAX-ACCESS  read-create
            STATUS  current
            DESCRIPTION
                " Setting it to  active(1) to creates an entry,setting it to destroy(2) to destroy an entry."
            ::= { qos2MapCostoIntp 9 } 
            
--xxx.100.27.1.2
    qos2MapCostoDP         	    OBJECT IDENTIFIER ::= { qos2 2 } 
    
--xxx.100.27.1.2.1
        qos2MapCostoDP1 OBJECT-TYPE
            SYNTAX  INTEGER
            MAX-ACCESS  read-create
            STATUS  current
            DESCRIPTION
                "COS to drop precedence map,Drop Precedence1<0-2>."
            ::= { qos2MapCostoDP  1 }

--xxx.100.27.1.2.2
	    qos2MapCostoDP2 OBJECT-TYPE
	        SYNTAX  INTEGER
	        MAX-ACCESS  read-create
	        STATUS  current
	        DESCRIPTION
	            "COS to drop precedence map,Drop Precedence2<0-2>."
	        ::= { qos2MapCostoDP  2 }

--xxx.100.27.1.2.3
	    qos2MapCostoDP3 OBJECT-TYPE
	        SYNTAX  INTEGER
	        MAX-ACCESS  read-create
	        STATUS  current
	        DESCRIPTION
	            "COS to drop precedence map,Drop Precedence3<0-2>."
	        ::= { qos2MapCostoDP  3 }

--xxx.100.27.1.2.4
	    qos2MapCostoDP4 OBJECT-TYPE
	        SYNTAX  INTEGER
	        MAX-ACCESS  read-create
	        STATUS  current
	        DESCRIPTION
	            "COS to drop precedence map,Drop Precedence4<0-2>."
	        ::= { qos2MapCostoDP  4 }

--xxx.100.27.1.2.5
	    qos2MapCostoDP5 OBJECT-TYPE
	        SYNTAX  INTEGER
	        MAX-ACCESS  read-create
	        STATUS  current
	        DESCRIPTION
	            "COS to drop precedence map,Drop Precedence5<0-2>."
	        ::= { qos2MapCostoDP  5 }

--xxx.100.27.1.2.6      
	    qos2MapCostoDP6 OBJECT-TYPE
	        SYNTAX  INTEGER
	        MAX-ACCESS  read-create
	        STATUS  current
	        DESCRIPTION
	            "COS to drop precedence map,Drop Precedence6<0-2>."
	        ::= { qos2MapCostoDP  6 }

--xxx.100.27.1.2.7        
	    qos2MapCostoDP7 OBJECT-TYPE
	        SYNTAX  INTEGER
	        MAX-ACCESS  read-create
	        STATUS  current
	        DESCRIPTION
	            "COS to drop precedence map,Drop Precedence7<0-2>."
	        ::= { qos2MapCostoDP  7 }

--xxx.100.27.1.2.8     
	    qos2MapCostoDP8 OBJECT-TYPE
	        SYNTAX  INTEGER
	        MAX-ACCESS  read-create
	        STATUS  current
	        DESCRIPTION
	            "COS to drop precedence map,Drop Precedence8<0-2>."
	        ::= { qos2MapCostoDP  8 }
                              
--xxx.100.27.1.2.9
        qos2MapCostoDPStatus OBJECT-TYPE
            SYNTAX  INTEGER
            	    {
               		active(1),
               		destroy(2)
            	    }
            MAX-ACCESS  read-create
            STATUS  current
            DESCRIPTION
                " Setting it to  active(1) to creates an entry,setting it to destroy(2) to destroy an entry."
            ::= { qos2MapCostoDP 9 }             

--xxx.100.27.1.3
    qos2MapDSCPtoDSCP         	    OBJECT IDENTIFIER ::= { qos2 3 } 
    
--xxx.100.27.1.3.1
        qos2MapDSCPtoDSCP1 OBJECT-TYPE
            SYNTAX  INTEGER
            MAX-ACCESS  read-create
            STATUS  current
            DESCRIPTION
                "DSCP to DSCP map, DSCP1<0-63>."
            ::= { qos2MapDSCPtoDSCP  1 }

--xxx.100.27.1.3.2
	    qos2MapDSCPtoDSCP2 OBJECT-TYPE
	        SYNTAX  INTEGER
	        MAX-ACCESS  read-create
	        STATUS  current
	        DESCRIPTION
	            "DSCP to DSCP map, DSCP2<0-63>."
	        ::= { qos2MapDSCPtoDSCP  2 }

--xxx.100.27.1.3.3
	    qos2MapDSCPtoDSCP3 OBJECT-TYPE
	        SYNTAX  INTEGER
	        MAX-ACCESS  read-create
	        STATUS  current
	        DESCRIPTION
	            "DSCP to DSCP map, DSCP3<0-63>."
	        ::= { qos2MapDSCPtoDSCP  3 }

--xxx.100.27.1.3.4
	    qos2MapDSCPtoDSCP4 OBJECT-TYPE
	        SYNTAX  INTEGER
	        MAX-ACCESS  read-create
	        STATUS  current
	        DESCRIPTION
	            "DSCP to DSCP map, DSCP4<0-63>."
	        ::= { qos2MapDSCPtoDSCP  4 }

--xxx.100.27.1.3.5
	    qos2MapDSCPtoDSCP5 OBJECT-TYPE
	        SYNTAX  INTEGER
	        MAX-ACCESS  read-create
	        STATUS  current
	        DESCRIPTION
	            "DSCP to DSCP map, DSCP5<0-63>."
	        ::= { qos2MapDSCPtoDSCP  5 }

--xxx.100.27.1.3.6      
	    qos2MapDSCPtoDSCP6 OBJECT-TYPE
	        SYNTAX  INTEGER
	        MAX-ACCESS  read-create
	        STATUS  current
	        DESCRIPTION
	            "DSCP to DSCP map, DSCP6<0-63>."
	        ::= { qos2MapDSCPtoDSCP  6 }

--xxx.100.27.1.3.7        
	    qos2MapDSCPtoDSCP7 OBJECT-TYPE
	        SYNTAX  INTEGER
	        MAX-ACCESS  read-create
	        STATUS  current
	        DESCRIPTION
	            "DSCP to DSCP map, DSCP7<0-63>."
	        ::= { qos2MapDSCPtoDSCP  7 }

--xxx.100.27.1.3.8     
	    qos2MapDSCPtoDSCP8 OBJECT-TYPE
	        SYNTAX  INTEGER
	        MAX-ACCESS  read-create
	        STATUS  current
	        DESCRIPTION
	            "DSCP to DSCP map, DSCP8<0-63>."
	        ::= { qos2MapDSCPtoDSCP 8 }

--xxx.100.27.1.3.9     
	    qos2MapDSCPtoDSCPoutDSCP OBJECT-TYPE
	        SYNTAX  INTEGER
	        MAX-ACCESS  read-create
	        STATUS  current
	        DESCRIPTION
	            "DSCP to DSCP map, outDSCP<0-63>."
	        ::= { qos2MapDSCPtoDSCP 9 }
	                                   
--xxx.100.27.1.3.10
        qos2MapDSCPtoDSCPStatus OBJECT-TYPE
            SYNTAX  INTEGER
            	    {
               		active(1),
               		destroy(2)
            	    }
            MAX-ACCESS  read-create
            STATUS  current
            DESCRIPTION
                " Setting it to  active(1) to creates an entry,setting it to destroy(2) to destroy an entry."
            ::= { qos2MapDSCPtoDSCP 10 }    
                     
--xxx.100.27.1.4
    qos2MapDSCPtoIntp        	    OBJECT IDENTIFIER ::= { qos2 4 } 
    
--xxx.100.27.1.4.1
        qos2MapDSCPtoIntp1 OBJECT-TYPE
            SYNTAX  INTEGER
            MAX-ACCESS  read-create
            STATUS  current
            DESCRIPTION
                "DSCP to Intp map, DSCP1<0-63>."
            ::= { qos2MapDSCPtoIntp  1 }

--xxx.100.27.1.4.2
	    qos2MapDSCPtoIntp2 OBJECT-TYPE
	        SYNTAX  INTEGER
	        MAX-ACCESS  read-create
	        STATUS  current
	        DESCRIPTION
	            "DSCP to Intp map, DSCP2<0-63>."
	        ::= { qos2MapDSCPtoIntp  2 }

--xxx.100.27.1.4.3
	    qos2MapDSCPtoIntp3 OBJECT-TYPE
	        SYNTAX  INTEGER
	        MAX-ACCESS  read-create
	        STATUS  current
	        DESCRIPTION
	            "DSCP to Intp map, DSCP3<0-63>."
	        ::= { qos2MapDSCPtoIntp  3 }

--xxx.100.27.1.4.4
	    qos2MapDSCPtoIntp4 OBJECT-TYPE
	        SYNTAX  INTEGER
	        MAX-ACCESS  read-create
	        STATUS  current
	        DESCRIPTION
	            "DSCP to Intp map, DSCP4<0-63>."
	        ::= { qos2MapDSCPtoIntp  4 }

--xxx.100.27.1.4.5
	    qos2MapDSCPtoIntp5 OBJECT-TYPE
	        SYNTAX  INTEGER
	        MAX-ACCESS  read-create
	        STATUS  current
	        DESCRIPTION
	            "DSCP to Intp map, DSCP5<0-63>."
	        ::= { qos2MapDSCPtoIntp  5 }

--xxx.100.27.1.4.6      
	    qos2MapDSCPtoIntp6 OBJECT-TYPE
	        SYNTAX  INTEGER
	        MAX-ACCESS  read-create
	        STATUS  current
	        DESCRIPTION
	            "DSCP to Intp map, DSCP6<0-63>."
	        ::= { qos2MapDSCPtoIntp  6 }

--xxx.100.27.1.4.7        
	    qos2MapDSCPtoIntp7 OBJECT-TYPE
	        SYNTAX  INTEGER
	        MAX-ACCESS  read-create
	        STATUS  current
	        DESCRIPTION
	            "DSCP to Intp map, DSCP7<0-63>."
	        ::= { qos2MapDSCPtoIntp  7 }

--xxx.100.27.1.4.8     
	    qos2MapDSCPtoIntp8 OBJECT-TYPE
	        SYNTAX  INTEGER
	        MAX-ACCESS  read-create
	        STATUS  current
	        DESCRIPTION
	            "DSCP to Intp map, DSCP8<0-63>."
	        ::= { qos2MapDSCPtoIntp 8 }

--xxx.100.27.1.4.9     
	    qos2MapDSCPtoIntpIntPriovalue OBJECT-TYPE
	        SYNTAX  INTEGER
	        MAX-ACCESS  read-create
	        STATUS  current
	        DESCRIPTION
	            "DSCP to Intp map, IntPrio value<0-7>."
	        ::= { qos2MapDSCPtoIntp 9 }
	                                   
--xxx.100.27.1.4.10
        qos2MapDSCPtoIntpStatus OBJECT-TYPE
            SYNTAX  INTEGER
            	    {
               		active(1),
               		destroy(2)
            	    }
            MAX-ACCESS  read-create
            STATUS  current
            DESCRIPTION
                " Setting it to  active(1) to creates an entry,setting it to destroy(2) to destroy an entry."
            ::= { qos2MapDSCPtoIntp 10 }            

--xxx.100.27.1.5
    qos2MapDSCPtoDP       	    OBJECT IDENTIFIER ::= { qos2 5 } 
    
--xxx.100.27.1.5.1
        qos2MapDSCPtoDP1 OBJECT-TYPE
            SYNTAX  INTEGER
            MAX-ACCESS  read-create
            STATUS  current
            DESCRIPTION
                "DSCP to DP map, DSCP1<0-63>."
            ::= { qos2MapDSCPtoDP  1 }

--xxx.100.27.1.5.2
	    qos2MapDSCPtoDP2 OBJECT-TYPE
	        SYNTAX  INTEGER
	        MAX-ACCESS  read-create
	        STATUS  current
	        DESCRIPTION
	            "DSCP to DP map, DSCP2<0-63>."
	        ::= { qos2MapDSCPtoDP  2 }

--xxx.100.27.1.5.3
	    qos2MapDSCPtoDP3 OBJECT-TYPE
	        SYNTAX  INTEGER
	        MAX-ACCESS  read-create
	        STATUS  current
	        DESCRIPTION
	            "DSCP to DP map, DSCP3<0-63>."
	        ::= { qos2MapDSCPtoDP  3 }

--xxx.100.27.1.5.4
	    qos2MapDSCPtoDP4 OBJECT-TYPE
	        SYNTAX  INTEGER
	        MAX-ACCESS  read-create
	        STATUS  current
	        DESCRIPTION
	            "DSCP to DP map, DSCP4<0-63>."
	        ::= { qos2MapDSCPtoDP  4 }

--xxx.100.27.1.5.5
	    qos2MapDSCPtoDP5 OBJECT-TYPE
	        SYNTAX  INTEGER
	        MAX-ACCESS  read-create
	        STATUS  current
	        DESCRIPTION
	            "DSCP to DP map, DSCP5<0-63>."
	        ::= { qos2MapDSCPtoDP  5 }

--xxx.100.27.1.5.6      
	    qos2MapDSCPtoDP6 OBJECT-TYPE
	        SYNTAX  INTEGER
	        MAX-ACCESS  read-create
	        STATUS  current
	        DESCRIPTION
	            "DSCP to DP map, DSCP6<0-63>."
	        ::= { qos2MapDSCPtoDP  6 }

--xxx.100.27.1.5.7        
	    qos2MapDSCPtoDP7 OBJECT-TYPE
	        SYNTAX  INTEGER
	        MAX-ACCESS  read-create
	        STATUS  current
	        DESCRIPTION
	            "DSCP to DP map, DSCP7<0-63>."
	        ::= { qos2MapDSCPtoDP  7 }

--xxx.100.27.1.5.8     
	    qos2MapDSCPtoDP8 OBJECT-TYPE
	        SYNTAX  INTEGER
	        MAX-ACCESS  read-create
	        STATUS  current
	        DESCRIPTION
	            "DSCP to DP map, DSCP8<0-63>."
	        ::= { qos2MapDSCPtoDP 8 }

--xxx.100.27.1.5.9     
	    qos2MapDSCPtoDPvalue OBJECT-TYPE
	        SYNTAX  INTEGER
	        MAX-ACCESS  read-create
	        STATUS  current
	        DESCRIPTION
	            "DSCP to DP map, Drop Precedence value<0-2>."
	        ::= { qos2MapDSCPtoDP 9 }
	                                   
--xxx.100.27.1.5.10
        qos2MapDSCPtoDPStatus OBJECT-TYPE
            SYNTAX  INTEGER
            	    {
               		active(1),
               		destroy(2)
            	    }
            MAX-ACCESS  read-create
            STATUS  current
            DESCRIPTION
                " Setting it to  active(1) to creates an entry,setting it to destroy(2) to destroy an entry."
            ::= { qos2MapDSCPtoDP 10 }            

--xxx.100.27.1.6
    qos2MapExptoIntp       	    OBJECT IDENTIFIER ::= { qos2 6 } 
    
--xxx.100.27.1.6.1
        qos2MapExptoIntp1 OBJECT-TYPE
            SYNTAX  INTEGER
            MAX-ACCESS  read-create
            STATUS  current
            DESCRIPTION
                "EXP to Intp map,  IntPrio1 value<0-7>."
            ::= { qos2MapExptoIntp  1 }

--xxx.100.27.1.6.2
	    qos2MapExptoIntp2 OBJECT-TYPE
	        SYNTAX  INTEGER
	        MAX-ACCESS  read-create
	        STATUS  current
	        DESCRIPTION
	            "EXP to Intp map,  IntPrio2 value<0-7>."
	        ::= { qos2MapExptoIntp  2 }

--xxx.100.27.1.6.3
	    qos2MapExptoIntp3 OBJECT-TYPE
	        SYNTAX  INTEGER
	        MAX-ACCESS  read-create
	        STATUS  current
	        DESCRIPTION
	            "EXP to Intp map,  IntPrio3 value<0-7>."
	        ::= { qos2MapExptoIntp  3 }

--xxx.100.27.1.6.4
	    qos2MapExptoIntp4 OBJECT-TYPE
	        SYNTAX  INTEGER
	        MAX-ACCESS  read-create
	        STATUS  current
	        DESCRIPTION
	            "EXP to Intp map,  IntPrio4 value<0-7>."
	        ::= { qos2MapExptoIntp  4 }

--xxx.100.27.1.6.5
	    qos2MapExptoIntp5 OBJECT-TYPE
	        SYNTAX  INTEGER
	        MAX-ACCESS  read-create
	        STATUS  current
	        DESCRIPTION
	            "EXP to Intp map,  IntPrio5 value<0-7>."
	        ::= { qos2MapExptoIntp  5 }

--xxx.100.27.1.6.6      
	    qos2MapExptoIntp6 OBJECT-TYPE
	        SYNTAX  INTEGER
	        MAX-ACCESS  read-create
	        STATUS  current
	        DESCRIPTION
	            "EXP to Intp map,  IntPrio6 value<0-7>."
	        ::= { qos2MapExptoIntp  6 }

--xxx.100.27.1.6.7        
	    qos2MapExptoIntp7 OBJECT-TYPE
	        SYNTAX  INTEGER
	        MAX-ACCESS  read-create
	        STATUS  current
	        DESCRIPTION
	            "EXP to Intp map,  IntPrio7 value<0-7>."
	        ::= { qos2MapExptoIntp  7 }

--xxx.100.27.1.6.8     
	    qos2MapExptoIntp8 OBJECT-TYPE
	        SYNTAX  INTEGER
	        MAX-ACCESS  read-create
	        STATUS  current
	        DESCRIPTION
	            "EXP to Intp map,  IntPrio8 value<0-7>."
	        ::= { qos2MapExptoIntp 8 }
	                                   
--xxx.100.27.1.6.9
        qos2MapExptoIntpStatus OBJECT-TYPE
            SYNTAX  INTEGER
            	    {
               		active(1),
               		destroy(2)
            	    }
            MAX-ACCESS  read-create
            STATUS  current
            DESCRIPTION
                " Setting it to  active(1) to creates an entry,setting it to destroy(2) to destroy an entry."
            ::= { qos2MapExptoIntp 9 }            

--xxx.100.27.1.7
    qos2MapExptoDP       	    OBJECT IDENTIFIER ::= { qos2 7 } 
    
--xxx.100.27.1.7.1
        qos2MapExptoDP1 OBJECT-TYPE
            SYNTAX  INTEGER
            MAX-ACCESS  read-create
            STATUS  current
            DESCRIPTION
                "EXP to DP map, Drop Precedence value<0-2>."
            ::= { qos2MapExptoDP  1 }

--xxx.100.27.1.7.2
	    qos2MapExptoDP2 OBJECT-TYPE
	        SYNTAX  INTEGER
	        MAX-ACCESS  read-create
	        STATUS  current
	        DESCRIPTION
	            "EXP to DP map, Drop Precedence value<0-2>."
	        ::= { qos2MapExptoDP  2 }

--xxx.100.27.1.7.3
	    qos2MapExptoDP3 OBJECT-TYPE
	        SYNTAX  INTEGER
	        MAX-ACCESS  read-create
	        STATUS  current
	        DESCRIPTION
	            "EXP to DP map, Drop Precedence value<0-2>."
	        ::= { qos2MapExptoDP  3 }

--xxx.100.27.1.7.4
	    qos2MapExptoDP4 OBJECT-TYPE
	        SYNTAX  INTEGER
	        MAX-ACCESS  read-create
	        STATUS  current
	        DESCRIPTION
	            "EXP to DP map, Drop Precedence value<0-2>."
	        ::= { qos2MapExptoDP  4 }

--xxx.100.27.1.7.5
	    qos2MapExptoDP5 OBJECT-TYPE
	        SYNTAX  INTEGER
	        MAX-ACCESS  read-create
	        STATUS  current
	        DESCRIPTION
	            "EXP to DP map, Drop Precedence value<0-2>."
	        ::= { qos2MapExptoDP  5 }

--xxx.100.27.1.7.6      
	    qos2MapExptoDP6 OBJECT-TYPE
	        SYNTAX  INTEGER
	        MAX-ACCESS  read-create
	        STATUS  current
	        DESCRIPTION
	            "EXP to DP map, Drop Precedence value<0-2>."
	        ::= { qos2MapExptoDP  6 }

--xxx.100.27.1.7.7        
	    qos2MapExptoDP7 OBJECT-TYPE
	        SYNTAX  INTEGER
	        MAX-ACCESS  read-create
	        STATUS  current
	        DESCRIPTION
	            "EXP to DP map, Drop Precedence value<0-2>."
	        ::= { qos2MapExptoDP  7 }

--xxx.100.27.1.7.8     
	    qos2MapExptoDP8 OBJECT-TYPE
	        SYNTAX  INTEGER
	        MAX-ACCESS  read-create
	        STATUS  current
	        DESCRIPTION
	            "EXP to DP map, Drop Precedence value<0-2>."
	        ::= { qos2MapExptoDP 8 }
	                                   
--xxx.100.27.1.7.9
        qos2MapExptoDPStatus OBJECT-TYPE
            SYNTAX  INTEGER
            	    {
               		active(1),
               		destroy(2)
            	    }
            MAX-ACCESS  read-create
            STATUS  current
            DESCRIPTION
                " Setting it to  active(1) to creates an entry,setting it to destroy(2) to destroy an entry."
            ::= { qos2MapExptoDP 9 }            

--xxx.100.27.1.8
    qos2MapIntptoDSCP       	    OBJECT IDENTIFIER ::= { qos2 8 } 
    
--xxx.100.27.1.8.1
        qos2MapIntptoDSCP1 OBJECT-TYPE
            SYNTAX  INTEGER
            MAX-ACCESS  read-create
            STATUS  current
            DESCRIPTION
                "Intp to DSCP map, IntPrio value<0-7>."
            ::= { qos2MapIntptoDSCP  1 }

--xxx.100.27.1.8.2
	    qos2MapIntptoDSCP2 OBJECT-TYPE
	        SYNTAX  INTEGER
	        MAX-ACCESS  read-create
	        STATUS  current
	        DESCRIPTION
	            "Intp to DSCP map, IntPrio value<0-7>."
	        ::= { qos2MapIntptoDSCP  2 }

--xxx.100.27.1.8.3
	    qos2MapIntptoDSCP3 OBJECT-TYPE
	        SYNTAX  INTEGER
	        MAX-ACCESS  read-create
	        STATUS  current
	        DESCRIPTION
	            "Intp to DSCP map, IntPrio value<0-7>."
	        ::= { qos2MapIntptoDSCP  3 }

--xxx.100.27.1.8.4
	    qos2MapIntptoDSCP4 OBJECT-TYPE
	        SYNTAX  INTEGER
	        MAX-ACCESS  read-create
	        STATUS  current
	        DESCRIPTION
	            "Intp to DSCP map, IntPrio value<0-7>."
	        ::= { qos2MapIntptoDSCP  4 }

--xxx.100.27.1.8.5
	    qos2MapIntptoDSCP5 OBJECT-TYPE
	        SYNTAX  INTEGER
	        MAX-ACCESS  read-create
	        STATUS  current
	        DESCRIPTION
	            "Intp to DSCP map, IntPrio value<0-7>."
	        ::= { qos2MapIntptoDSCP  5 }

--xxx.100.27.1.8.6      
	    qos2MapIntptoDSCP6 OBJECT-TYPE
	        SYNTAX  INTEGER
	        MAX-ACCESS  read-create
	        STATUS  current
	        DESCRIPTION
	            "Intp to DSCP map, IntPrio value<0-7>."
	        ::= { qos2MapIntptoDSCP  6 }

--xxx.100.27.1.8.7        
	    qos2MapIntptoDSCP7 OBJECT-TYPE
	        SYNTAX  INTEGER
	        MAX-ACCESS  read-create
	        STATUS  current
	        DESCRIPTION
	            "Intp to DSCP map, IntPrio value<0-7>."
	        ::= { qos2MapIntptoDSCP  7 }

--xxx.100.27.1.8.8     
	    qos2MapIntptoDSCP8 OBJECT-TYPE
	        SYNTAX  INTEGER
	        MAX-ACCESS  read-create
	        STATUS  current
	        DESCRIPTION
	            "Intp to DSCP map, IntPrio value<0-7>."
	        ::= { qos2MapIntptoDSCP 8 }
	                                   
--xxx.100.27.1.8.9
        qos2MapIntptoDSCPStatus OBJECT-TYPE
            SYNTAX  INTEGER
            	    {
               		active(1),
               		destroy(2)
            	    }
            MAX-ACCESS  read-create
            STATUS  current
            DESCRIPTION
                " Setting it to  active(1) to creates an entry,setting it to destroy(2) to destroy an entry."
            ::= { qos2MapIntptoDSCP 9 }            

--xxx.100.27.1.10
    qos2MapIntptoEXP       	    OBJECT IDENTIFIER ::= { qos2 10 } 
    
--xxx.100.27.1.10.1
        qos2MapIntptoEXP1 OBJECT-TYPE
            SYNTAX  INTEGER
            MAX-ACCESS  read-create
            STATUS  current
            DESCRIPTION
                "Intp to EXP map, EXP value<0-7>."
            ::= { qos2MapIntptoEXP  1 }

--xxx.100.27.1.10.2
	    qos2MapIntptoEXP2 OBJECT-TYPE
	        SYNTAX  INTEGER
	        MAX-ACCESS  read-create
	        STATUS  current
	        DESCRIPTION
	            "Intp to EXP map, EXP value<0-7>."
	        ::= { qos2MapIntptoEXP  2 }

--xxx.100.27.1.10.3
	    qos2MapIntptoEXP3 OBJECT-TYPE
	        SYNTAX  INTEGER
	        MAX-ACCESS  read-create
	        STATUS  current
	        DESCRIPTION
	            "Intp to EXP map, EXP value<0-7>."
	        ::= { qos2MapIntptoEXP  3 }

--xxx.100.27.1.10.4
	    qos2MapIntptoEXP4 OBJECT-TYPE
	        SYNTAX  INTEGER
	        MAX-ACCESS  read-create
	        STATUS  current
	        DESCRIPTION
	            "Intp to EXP map, EXP value<0-7>."
	        ::= { qos2MapIntptoEXP  4 }

--xxx.100.27.1.10.5
	    qos2MapIntptoEXP5 OBJECT-TYPE
	        SYNTAX  INTEGER
	        MAX-ACCESS  read-create
	        STATUS  current
	        DESCRIPTION
	            "Intp to EXP map, EXP value<0-7>."
	        ::= { qos2MapIntptoEXP  5 }

--xxx.100.27.1.10.6      
	    qos2MapIntptoEXP6 OBJECT-TYPE
	        SYNTAX  INTEGER
	        MAX-ACCESS  read-create
	        STATUS  current
	        DESCRIPTION
	            "Intp to EXP map, EXP value<0-7>."
	        ::= { qos2MapIntptoEXP  6 }

--xxx.100.27.1.10.7        
	    qos2MapIntptoEXP7 OBJECT-TYPE
	        SYNTAX  INTEGER
	        MAX-ACCESS  read-create
	        STATUS  current
	        DESCRIPTION
	            "Intp to EXP map, EXP value<0-7>."
	        ::= { qos2MapIntptoEXP  7 }

--xxx.100.27.1.10.8     
	    qos2MapIntptoEXP8 OBJECT-TYPE
	        SYNTAX  INTEGER
	        MAX-ACCESS  read-create
	        STATUS  current
	        DESCRIPTION
	            "Intp to EXP map, EXP value<0-7>."
	        ::= { qos2MapIntptoEXP 8 }
	                                   
--xxx.100.27.1.10.9
        qos2MapIntptoEXPStatus OBJECT-TYPE
            SYNTAX  INTEGER
            	    {
               		active(1),
               		destroy(2)
            	    }
            MAX-ACCESS  read-create
            STATUS  current
            DESCRIPTION
                " Setting it to  active(1) to creates an entry,setting it to destroy(2) to destroy an entry."
            ::= { qos2MapIntptoEXP 9 }                  

--xxx.100.27.1.11
    qos2AggregatePolicy       	    OBJECT IDENTIFIER ::= { qos2 11 } 
    
--xxx.100.27.1.11.1
        qos2AggPolicyName OBJECT-TYPE
            SYNTAX  DisplayString (SIZE(1..64))
            MAX-ACCESS  read-create
            STATUS  current
            DESCRIPTION
                "Aggregate policy name<1-64>."
            ::= { qos2AggregatePolicy  1 }

--xxx.100.27.1.11.2
	    qos2AggPolicyCIRKbps OBJECT-TYPE
	        SYNTAX  INTEGER
	        MAX-ACCESS  read-create
	        STATUS  current
	        DESCRIPTION
	            "CIR(Committed Information Rate) Kbits per second <1-10000000>."
	        ::= { qos2AggregatePolicy  2 }

--xxx.100.27.1.11.3
	    qos2AggPolicyCBSKbps OBJECT-TYPE
	        SYNTAX  INTEGER
	        MAX-ACCESS  read-create
	        STATUS  current
	        DESCRIPTION
	            "CBS(Committed Burst Size) Kbits per second <1-1000000>."
	        ::= { qos2AggregatePolicy  3 }

--xxx.100.27.1.11.4
	    qos2AggPolicyPBSKbps OBJECT-TYPE
	        SYNTAX  INTEGER
	        MAX-ACCESS  read-create
	        STATUS  current
	        DESCRIPTION
	            "PBS(Peak Burst Size) Kbits per second <1-1000000>."
	        ::= { qos2AggregatePolicy  4 }

--xxx.100.27.1.11.5
	    qos2AggPolicyPIRKbps OBJECT-TYPE
	        SYNTAX  INTEGER
	        MAX-ACCESS  read-create
	        STATUS  current
	        DESCRIPTION
	            "PIR(Peak Information Rate) Kbits per second <1-10000000>."
	        ::= { qos2AggregatePolicy  5 }

--xxx.100.27.1.11.6      
	    qos2AggPolicyConformAction OBJECT-TYPE
	        SYNTAX  INTEGER
            	{
            	    transmit(0),
            	    drop(1),
               		set-dscp-transmit(2), 
               		set-prec-transmit(3),
               		set-cos-transmit(4), 
               		set-drop-precedence(5),
               		set-internal-priority(6)           		      	
            	}
	        MAX-ACCESS  read-create
	        STATUS  current
	        DESCRIPTION
	            "conform-action transmit means send packets without any change when specified speed is not exceeded; 
	             conform-action drop means drop packets when specified speed is not exceeded; 
	             conform-action set-dscp-transmit specifies to mark down packet DSCP value according to policed-dscp mapping when specified speed is not exceeded; 
	             conform-action set-prec-transmit specifies to mark down packet TOS value according to policed-dscp mapping when specified speed is not exceeded.
                ."
	        ::= { qos2AggregatePolicy  6 }

--xxx.100.27.1.11.7        
	    qos2AggPolicyConformActionChangeValue OBJECT-TYPE
	        SYNTAX  INTEGER
	        MAX-ACCESS  read-create
	        STATUS  current
	        DESCRIPTION
	            "If conform-action is set-dscp-transmit(2),the value is between 0-63; 
	             If conform-action is set-prec-transmit(3),the value is between 0-7;
	             If conform-action is set-cos-transmit(4),the value is between 0-7;
	             If conform-action is set-drop-precedence(5),the value is between 0-2;
	             If conform-action is set-internal-priority(6),the value is between 0-7;"
	        ::= { qos2AggregatePolicy  7 }

--xxx.100.27.1.11.8      
	    qos2AggPolicyExceedAction OBJECT-TYPE
	        SYNTAX  INTEGER
            	{
            	    transmit(0),
            	    drop(1),
               		set-dscp-transmit(2), 
               		set-prec-transmit(3),
               		set-cos-transmit(4), 
               		set-drop-precedence(5),
               		set-internal-priority(6)           		      	
            	}
	        MAX-ACCESS  read-create
	        STATUS  current
	        DESCRIPTION
	            "conform-action transmit means send packets without any change when specified speed is not exceeded; 
	             conform-action drop means drop packets when specified speed is not exceeded; 
	             conform-action set-dscp-transmit specifies to mark down packet DSCP value according to policed-dscp mapping when specified speed is not exceeded; 
	             conform-action set-prec-transmit specifies to mark down packet TOS value according to policed-dscp mapping when specified speed is not exceeded.
                ."
	        ::= { qos2AggregatePolicy  8 }

--xxx.100.27.1.11.9        
	    qos2AggPolicyExceedActionChangeValue OBJECT-TYPE
	        SYNTAX  INTEGER
	        MAX-ACCESS  read-create
	        STATUS  current
	        DESCRIPTION
	            "If conform-action is set-dscp-transmit(2),the value is between 0-63; 
	             If conform-action is set-prec-transmit(3),the value is between 0-7;
	             If conform-action is set-cos-transmit(4),the value is between 0-7;
	             If conform-action is set-drop-precedence(5),the value is between 0-2;
	             If conform-action is set-internal-priority(6),the value is between 0-7;"
	        ::= { qos2AggregatePolicy  9 }
	        
--xxx.100.27.1.11.10      
	    qos2AggPolicyViolateAction OBJECT-TYPE
	        SYNTAX  INTEGER
            	{
            	    transmit(0),
            	    drop(1),
               		set-dscp-transmit(2), 
               		set-prec-transmit(3),
               		set-cos-transmit(4), 
               		set-drop-precedence(5),
               		set-internal-priority(6)           		      	
            	}
	        MAX-ACCESS  read-create
	        STATUS  current
	        DESCRIPTION
	            "conform-action transmit means send packets without any change when specified speed is not exceeded; 
	             conform-action drop means drop packets when specified speed is not exceeded; 
	             conform-action set-dscp-transmit specifies to mark down packet DSCP value according to policed-dscp mapping when specified speed is not exceeded; 
	             conform-action set-prec-transmit specifies to mark down packet TOS value according to policed-dscp mapping when specified speed is not exceeded.
                ."
	        ::= { qos2AggregatePolicy  10 }

--xxx.100.27.1.11.11        
	    qos2AggPolicyViolateActionChangeValue OBJECT-TYPE
	        SYNTAX  INTEGER
	        MAX-ACCESS  read-create
	        STATUS  current
	        DESCRIPTION
	            "If conform-action is set-dscp-transmit(2),the value is between 0-63; 
	             If conform-action is set-prec-transmit(3),the value is between 0-7;
	             If conform-action is set-cos-transmit(4),the value is between 0-7;
	             If conform-action is set-drop-precedence(5),the value is between 0-2;
	             If conform-action is set-internal-priority(6),the value is between 0-7;"
	        ::= { qos2AggregatePolicy  11 }	        

--xxx.100.27.1.11.12
        qos2AggPolicyStatus OBJECT-TYPE
            SYNTAX  INTEGER
            	    {
               		active(1),
               		destroy(2)
            	    }
            MAX-ACCESS  read-create
            STATUS  current
            DESCRIPTION
                " Setting it to  active(1) to creates an entry,setting it to destroy(2) to destroy an entry."
            ::= { qos2AggregatePolicy 12 }          


--xxx.100.27.1.12
qos2ServicePolicyTable OBJECT-TYPE
    SYNTAX  SEQUENCE OF Qos2ServicePolicyEntry
    MAX-ACCESS  not-accessible
    STATUS  current
    DESCRIPTION
    	" QoS service policy table."
    ::= { qos2  12}   

--xxx.100.27.1.12.1
qos2ServicePolicyEntry OBJECT-TYPE
        SYNTAX  Qos2ServicePolicyEntry
        MAX-ACCESS  not-accessible
        STATUS  current
        DESCRIPTION
            " QoS service policy table."
        INDEX   { qos2PolicyMapName }
        ::= { qos2ServicePolicyTable 1 }
        
Qos2ServicePolicyEntry
        ::= SEQUENCE
            {
            qos2PolicyMapName	             DisplayString ,
    		qos2ServicePolicyVlanList         DisplayString , 
    		qos2ServicePolicyStatus	         INTEGER			
            }
 
--xxx.100.27.1.12.1.1
qos2PolicyMapName OBJECT-TYPE
    SYNTAX  DisplayString (SIZE(1..64)) 
            MAX-ACCESS  read-only
            STATUS  current
            DESCRIPTION
                "Policy map name<1-64>."
            ::= { qos2ServicePolicyEntry 1 }

        
--xxx.100.27.1.12.1.2
qos2ServicePolicyVlanList OBJECT-TYPE
    SYNTAX  DisplayString 
            MAX-ACCESS  read-only
            STATUS  current
            DESCRIPTION
                "Vlan list."
            ::= { qos2ServicePolicyEntry 2 } 

--xxx.100.27.1.12.1.3
qos2ServicePolicyStatus OBJECT-TYPE
    SYNTAX  INTEGER 
        	    {
           		active(1),
           		destroy(2)
        	    }
            MAX-ACCESS  read-create
            STATUS  current
            DESCRIPTION
                " Setting it to  active(1) to creates an entry,setting it to destroy(2) to destroy an entry."
            ::= { qos2ServicePolicyEntry 3 } 
	                                               
--xxx.100.27.1.13
qos2PortTable         	    OBJECT IDENTIFIER ::= { qos2 13 } 

--xxx.100.27.1.13.1
qos2PortIndex OBJECT-TYPE
    SYNTAX  INTEGER (1..10000)
            MAX-ACCESS  read-create
            STATUS  current
            DESCRIPTION
                "port Index"
            ::= { qos2PortTable 1 } 

--xxx.100.27.1.13.2
qos2PortType OBJECT-TYPE
    SYNTAX  INTEGER
                {
            	          trust(0),                
            		  cos(1),
            		  policy(2),            		  
 			  queueAndBandwidth(3),
               		  queueAndAlgorithm(4), 			  
               		  queueAndWdrr(5),
               		  queueAndWrr(6)
            	}
            MAX-ACCESS  read-create
            STATUS  current
            DESCRIPTION
                "the relation between qosPortType and CLI:
 		0 mls qos trust {cos |dscp };               
                1 mls qos cos {<default-cos>};     
		2 service-policy input WORD;
		3 mls qos queue {<queue id>} bandwidth {<MinBandwidth> <MaxBandwidth>};
		4 mls qos queue algorithm {sp |wdrr |wrr };
		5 mls qos queue wdrr weight {<Queue1 bandwidth> <Queue2 bandwidth> <Queue3 bandwidth> <Queue4 bandwidth> <Queue5 bandwidth> <Queue6 bandwidth> <Queue7 bandwidth> <Queue8 bandwidth>};
		6 mls qos queue wrr weight {<Queue1 weight> <Queue2 weight> <Queue3 weight> <Queue4 weight> <Queue5 weight> <Queue6 weight> <Queue7 weight> <Queue8 weight>}.						
		According to the relation,when configurate qos with snmp,first set the qosPortType to the correct value to select CLI,
		then set next CLI parameter.Fox example,set qos default cos is 5, first set qosPortType=1 ,then set qosPortCos to 5,
		finally setting qosPortStatus to 1, trigger snmp-cache works."
            ::= { qos2PortTable 2 }  
                               
--xxx.100.27.1.13.3
qos2PortCos OBJECT-TYPE
    SYNTAX  INTEGER(0..7)
            MAX-ACCESS  read-create
            STATUS  current
            DESCRIPTION
                "port default cos value"
            ::= { qos2PortTable 3 } 

--xxx.100.27.1.13.4
qos2PortTrust OBJECT-TYPE
    SYNTAX  INTEGER
            	{
               		cos(0),
               		dscp(1)
            	}
            MAX-ACCESS  read-create
            STATUS  current
            DESCRIPTION
                "Configure port trust.
            	  cos(0),mls qos trust cos;
               	  dscp(1),mls qos trust dscp."
            ::= { qos2PortTable 4 } 
            
--xxx.100.27.1.13.5
qos2PortPolicy OBJECT-TYPE
    SYNTAX  DisplayString
            MAX-ACCESS  read-create
            STATUS  current
            DESCRIPTION
                "The corresponding CLI:service-policy input WORD."
            ::= { qos2PortTable 5 }             

--xxx.100.27.1.13.6
qos2PortQueueBandwidth OBJECT-TYPE
    SYNTAX  DisplayString
            MAX-ACCESS  read-create
            STATUS  current
            DESCRIPTION
                "The corresponding CLI:mls qos queue {<queue id>} bandwidth {<MinBandwidth> <MaxBandwidth>}."  
            ::= { qos2PortTable 6 } 

--xxx.100.27.1.13.7
qos2PortQueueAlgorithm OBJECT-TYPE
    SYNTAX  INTEGER
            	{
               		sp(0),
               		wdrr(1),
               		wrr(2)               		
            	}
    	    MAX-ACCESS  read-create
    	    STATUS  current
            DESCRIPTION
                "The corresponding CLI:mls qos queue algorithm {sp |wdrr |wrr }."
            ::= { qos2PortTable 7 } 
            
--xxx.100.27.1.13.8
qos2PortQueueWdrr OBJECT-TYPE
    SYNTAX  DisplayString
            MAX-ACCESS  read-create
            STATUS  current
            DESCRIPTION
                "The corresponding CLI:mls qos queue wdrr weight {<Queue1 bandwidth> <Queue2 bandwidth> <Queue3 bandwidth> <Queue4 bandwidth> <Queue5 bandwidth> <Queue6 bandwidth> <Queue7 bandwidth> <Queue8 bandwidth>}."
            ::= { qos2PortTable 8 }   
            
--xxx.100.27.1.13.9
qos2PortQueueWrr OBJECT-TYPE
    SYNTAX  DisplayString
            MAX-ACCESS  read-create
            STATUS  current
            DESCRIPTION
                "The corresponding CLI:mls qos queue wrr weight {<Queue1 weight> <Queue2 weight> <Queue3 weight> <Queue4 weight> <Queue5 weight> <Queue6 weight> <Queue7 weight> <Queue8 weight>}." 
            ::= { qos2PortTable 9 }                        

--xxx.100.27.1.13.10
qos2PortStatus OBJECT-TYPE
            SYNTAX  INTEGER
            	    {
               		active(1),
               		destroy(2)
            	    }
            MAX-ACCESS  read-create
            STATUS  current
            DESCRIPTION
                " Setting it to  active(1) to creates an entry,setting it to destroy(2) to destroy an entry."
            ::= { qos2PortTable 10 }   

                                            
--********************************************************************************************************    
--xxx.100.27.1.14
qos2ClassMapTable         	    OBJECT IDENTIFIER ::= { qos2 14 } 

--xxx.100.27.1.14.1
        qos2ClassMapName OBJECT-TYPE
            SYNTAX  DisplayString (SIZE(1..64))
            MAX-ACCESS  read-create
            STATUS  current
            DESCRIPTION
                "classmap name"
            ::= { qos2ClassMapTable 1}

--xxx.100.27.1.14.2
        qos2ClassMapType OBJECT-TYPE
            SYNTAX  INTEGER
            	{
            	    configurClassMap(0),
            	    accessGroup(1),
               	    dscp(2),
               	    v6dscp(5),
               	    ippre(3),
               	    v6AccessGroup(8),
               	    v6Flow(7),
               	    vlan(4), 
               	    cos(9),
               	    exp(10)
            	}
            MAX-ACCESS  read-create
            STATUS  current
            DESCRIPTION
                "0 class-map <class-map-name>,index is classmapname;
		1 match access-group <acl-index-or-name>,need qos2ClassMapAccessGroup cooperation;
		2 match ip dscp <dscp-list>,need qos2ClassMapDscp cooperation;
		3 match ip precedence <ip-precedence-list>,need qos2ClassMapIpPre cooperation;
		4 match vlan <vlan-list>,need qos2ClassMapVlan cooperation;
		5 match ipv6 dscp <dscp-list>,need qos2ClassMapV6Dscp cooperation;
		7 match ipv6 flowlabel,need qos2ClassMapV6Flow cooperation;
		8 match ipv6 access-group,need qos2ClassMapV6AccGroup cooperation;
		9 match cos,need qos2ClassCos cooperation;
	        10 match exp <exp-list>,need qos2ClassMapExp cooperation."
            ::= { qos2ClassMapTable  2 }

--xxx.100.27.1.14.3
        qos2ClassMapAccessGroup OBJECT-TYPE
            SYNTAX  DisplayString
            MAX-ACCESS  read-create
            STATUS  current
            DESCRIPTION
                "Match specify access-group (name or number). 
                This object be configured only if qosClassMapType  
                in the same row is accessGroup(1)."
            ::= { qos2ClassMapTable 3 }
            
--xxx.100.27.1.14.4
        qos2ClassMapDscp OBJECT-TYPE
            SYNTAX  DisplayString
            MAX-ACCESS  read-create
            STATUS  current
            DESCRIPTION
                "Match specify Dscp.
                This object be configured only if qosClassMapType 
                in the same row is dscp(2)."
            ::= { qos2ClassMapTable  4 }  
                      
--xxx.100.27.1.14.5
        qos2ClassMapV6Dscp OBJECT-TYPE
            SYNTAX  DisplayString
            MAX-ACCESS  read-create
            STATUS  current
            DESCRIPTION
                "Match specify ipv6 Dscp.
                This object be configured only if qosClassMapType 
                in the same row is v6dscp(5)."
            ::= { qos2ClassMapTable  5 } 
            
--xxx.100.27.1.14.6
        qos2ClassMapIpPre OBJECT-TYPE
            SYNTAX  DisplayString
            MAX-ACCESS  read-create
            STATUS  current
            DESCRIPTION
                "Match specify Ip Precedence.
                This object be configured only if qosClassMapType 
                in the same row is ippre(3)."
            ::= { qos2ClassMapTable  6 } 
            
--xxx.100.27.1.14.7
        qos2ClassMapV6AccGroup OBJECT-TYPE
            SYNTAX  DisplayString
            MAX-ACCESS  read-create
            STATUS  current
            DESCRIPTION
                "Match specify Ipv6 Access-Group.
                This object be configured only if qosClassMapType  
                in the same row is v6AccessGroup(8)."
            ::= { qos2ClassMapTable  7 } 
            
--xxx.100.27.1.14.8
        qos2ClassMapV6Flow OBJECT-TYPE
            SYNTAX  DisplayString
            MAX-ACCESS  read-create
            STATUS  current
            DESCRIPTION
                "Match specify Ipv6 Flowlabel.
                This object be configured only if qosClassMapType  
                in the same row is v6Flow(6)."
            ::= { qos2ClassMapTable  8 } 
            
--xxx.100.27.1.14.9
        qos2ClassMapVlan OBJECT-TYPE
            SYNTAX  DisplayString
            MAX-ACCESS  read-create
            STATUS  current
            DESCRIPTION
                "Match specify Vlan list . At most 8 vlan id.
                This object be configured only if qosClassMapType  
                in the same row is vlan(4)."
            ::= { qos2ClassMapTable  9 } 
     
--xxx.100.27.1.1410
        qos2ClassMapCos OBJECT-TYPE
            SYNTAX  DisplayString
            MAX-ACCESS  read-create
            STATUS  current
            DESCRIPTION
                "Match specify Cos .
                This object be configured only if qosClassMapType  
                in the same row is cos(9)."
            ::= { qos2ClassMapTable 10 }

--xxx.100.27.1.14.11
        qos2ClassMapExp  OBJECT-TYPE
            SYNTAX  DisplayString
            MAX-ACCESS  read-create
            STATUS  current
            DESCRIPTION
                "Match specify MPLS EXP.
                This object be configured only if qosClassMapType  
                in the same row is Exp(10)."
            ::= { qos2ClassMapTable 11 }  	        
               
--xxx.100.27.1.14.12
        qos2ClassMapStatus OBJECT-TYPE
            SYNTAX  INTEGER
            	    {
               		active(1),
               		destroy(2)
            	    }
            MAX-ACCESS  read-create
            STATUS  current
            DESCRIPTION
                " Setting it to  active(1) to creates an entry,setting it to destroy(2) to destroy an entry."
            ::= { qos2ClassMapTable 12 } 
            
--********************************************************************************************************

--xxx.100.27.1.15
qos2PolicyTable         	    OBJECT IDENTIFIER ::= { qos2 15 } 

--xxx.100.27.1.15.1
        qos2PolicyName OBJECT-TYPE
            SYNTAX  DisplayString (SIZE(1..64))
            MAX-ACCESS  read-create
            STATUS  current
            DESCRIPTION
                "QoS Policy name"
            ::= { qos2PolicyTable 1 }

--xxx.100.27.1.15.2
        qos2PolicyClassMap OBJECT-TYPE
            SYNTAX  DisplayString (SIZE(1..64))
            MAX-ACCESS  read-create
            STATUS  current
            DESCRIPTION
                "Specify the classmap name.After a policy map is created, it can be associated to a class.
                So, if you want the class map to match the policy map,please setting the qosPolicyType to 1,and then
                setting the qosPolicyStatus to 1 ."
            ::= { qos2PolicyTable 2 }
            
--xxx.100.27.1.15.3
        qos2PolicyInsertClassMap OBJECT-TYPE
            SYNTAX  DisplayString (SIZE(1..64))
            MAX-ACCESS  read-create
            STATUS  current
            DESCRIPTION
                "Specify the position of classmap name."
            ::= { qos2PolicyTable 3 }            

--xxx.100.27.1.15.4
        qos2PolicyType OBJECT-TYPE
            SYNTAX  INTEGER            	
            	{
            	    	policymap(0),
            	    	matchclassmap(1),
            	    	threeColor(2),
               		aggregatePolicer(3), 
               		accounting(4)               		        	
            	}
            MAX-ACCESS  read-create
            STATUS  current
            DESCRIPTION
                "the relation between qosPolicyType and CLI:
		0  policy-map <policy-map-name>;
		1  class <class-map-name>;
		2  policy <bits_per_second> <normal_burst_bytes> [pir <peak_rate_bps>] |  <maximum_burst_bytes> [{conform-action ACTION | exceed-action ACTION | violate-action ACTION }];
		3  policy aggregate <aggregate-policer-name>; 
		4  accounting. " 
            ::= { qos2PolicyTable 4 }
            
--xxx.100.27.1.15.5
        qos2PolicyCIRKbps OBJECT-TYPE
            SYNTAX  INTEGER(1..10000000)
            MAX-ACCESS  read-create
            STATUS  current
            DESCRIPTION
                "CIR(Committed Information Rate) Kbits per second <1-10000000>."
            ::= { qos2PolicyTable 5 }            

--xxx.100.27.1.15.6
        qos2PolicyCBSKbps OBJECT-TYPE
            SYNTAX  INTEGER(1..1000000)
            MAX-ACCESS  read-create
            STATUS  current
            DESCRIPTION
                "CBS(Committed Burst Size) Kbits per second <1-1000000>."
            ::= { qos2PolicyTable 6 }
            
--xxx.100.27.1.15.7
        qos2PolicyPBSKbps OBJECT-TYPE
            SYNTAX  INTEGER(1..1000000)
            MAX-ACCESS  read-create
            STATUS  current
            DESCRIPTION
                "PBS(Peak Burst Size) Kbits per second <1-1000000>."
            ::= { qos2PolicyTable 7 }
            
--xxx.100.27.1.15.8
        qos2PolicyPIRKbps OBJECT-TYPE
            SYNTAX  INTEGER(1..10000000)
            MAX-ACCESS  read-create
            STATUS  current
            DESCRIPTION
                "PIR(Peak Information Rate) Kbits per second <1-10000000>."
            ::= { qos2PolicyTable 8 }                                                                         

--xxx.100.27.1.15.9
        qos2PolicyConformActionChange OBJECT-TYPE
            SYNTAX  INTEGER
            	{
            	        transmit(0),
            	    	drop(1),
               		set-dscp-transmit(2), 
               		set-prec-transmit(3),
  			set-cos-transmit(4),
			set-internal-priority(5), 
			set-drop-Precedence(6)        	
            	}
            MAX-ACCESS  read-create
            STATUS  current
            DESCRIPTION
                "transmit(0): means send packets without any change;
		drop(1): means drop packets;
		set-dscp-transmit(2): send packets and remark dscp value;
		set-prec-transmit(3): send packets and remark ip-precedence value;
		set-cos-transmit(4): send packets and remark cos value;
		set-internal-priority(5):send packets and remark internal-priority value ;
		set-drop-Precedence(6): send packets and remark drop-precedence value."               
            ::= { qos2PolicyTable 9 }            
            
--xxx.100.27.1.15.10
        qos2PolicyConformActionChangeValue OBJECT-TYPE
            SYNTAX  INTEGER (0..63) 
            MAX-ACCESS  read-create
            STATUS  current
            DESCRIPTION
                "If action is set-dscp-transmit(2),the value is between 0-63;
                 else if action is set-prec-transmit(3),the value is between 0-7;
                 else if action is set-cos-transmit(4),the value is between 0-7;
                 else if action is set-internal-priority(5),the value is between 0-7;
                 else if action is set-drop-Precedence(6),the value is between 0-2."
            ::= { qos2PolicyTable 10 }   
            
--xxx.100.27.1.15.11
        qos2PolicyExceedActionChange OBJECT-TYPE
            SYNTAX  INTEGER
            	{
            	        transmit(0),
            	    	drop(1),
               		set-dscp-transmit(2), 
               		set-prec-transmit(3),
  			set-cos-transmit(4),
			set-internal-priority(5), 
			set-drop-Precedence(6)        	
            	}
            MAX-ACCESS  read-create
            STATUS  current
            DESCRIPTION
                "transmit(0): means send packets without any change;
		drop(1): means drop packets;
		set-dscp-transmit(2): send packets and remark dscp value;
		set-prec-transmit(3): send packets and remark ip-precedence value;
		set-cos-transmit(4): send packets and remark cos value;
		set-internal-priority(5):send packets and remark internal-priority value ;
		set-drop-Precedence(6): send packets and remark drop-precedence value."               
            ::= { qos2PolicyTable 11 }            
            
--xxx.100.27.1.15.12
        qos2PolicyExceedActionChangeValue OBJECT-TYPE
            SYNTAX  INTEGER (0..63) 
            MAX-ACCESS  read-create
            STATUS  current
            DESCRIPTION
                "If action is set-dscp-transmit(2),the value is between 0-63;
                 else if action is set-prec-transmit(3),the value is between 0-7;
                 else if action is set-cos-transmit(4),the value is between 0-7;
                 else if action is set-internal-priority(5),the value is between 0-7;
                 else if action is set-drop-Precedence(6),the value is between 0-2."
            ::= { qos2PolicyTable 12 }  
            
--xxx.100.27.1.15.13
        qos2PolicyViolateActionChange OBJECT-TYPE
            SYNTAX  INTEGER
            	{
            	        transmit(0),
            	    	drop(1),
               		set-dscp-transmit(2), 
               		set-prec-transmit(3),
  			set-cos-transmit(4),
			set-internal-priority(5), 
			set-drop-Precedence(6)        	
            	}
            MAX-ACCESS  read-create
            STATUS  current
            DESCRIPTION
                "transmit(0): means send packets without any change;
		drop(1): means drop packets;
		set-dscp-transmit(2): send packets and remark dscp value;
		set-prec-transmit(3): send packets and remark ip-precedence value;
		set-cos-transmit(4): send packets and remark cos value;
		set-internal-priority(5):send packets and remark internal-priority value ;
		set-drop-Precedence(6): send packets and remark drop-precedence value."               
            ::= { qos2PolicyTable 13 }            
            
--xxx.100.27.1.15.14
        qos2PolicyViolateActionChangeValue OBJECT-TYPE
            SYNTAX  INTEGER (0..63) 
            MAX-ACCESS  read-create
            STATUS  current
            DESCRIPTION
                "If action is set-dscp-transmit(2),the value is between 0-63;
                 else if action is set-prec-transmit(3),the value is between 0-7;
                 else if action is set-cos-transmit(4),the value is between 0-7;
                 else if action is set-internal-priority(5),the value is between 0-7;
                 else if action is set-drop-Precedence(6),the value is between 0-2."
            ::= { qos2PolicyTable 14 }                                                    

--xxx.100.27.1.15.15
        qos2PolicyAggregatePolicer OBJECT-TYPE
            SYNTAX  DisplayString
            MAX-ACCESS  read-create
            STATUS  current
            DESCRIPTION
                "aggregate-policer-name.
                This object be configured only if qosPolicyType 
                in the same row is aggregatePolicer(3)."
            ::= { qos2PolicyTable 15 }   

--xxx.100.27.1.15.16
        qos2PolicyStatus OBJECT-TYPE
            SYNTAX  INTEGER
            	    {
               		active(1),
               		destroy(2)
            	    }
            MAX-ACCESS  read-create
            STATUS  current
            DESCRIPTION
                " Setting it to  active(1) to creates an entry,setting it to destroy(2) to destroy an entry."
            ::= { qos2PolicyTable 16 } 

--******************************************************************************************************** 


--********************************************************************************************************                        
--xxx.100.27.1.16
qos2SetTable         	    OBJECT IDENTIFIER ::= { qos2 16 } 

--xxx.100.27.1.16.1
        qos2SetPolicyMapName OBJECT-TYPE
            SYNTAX  DisplayString (SIZE(1..32))
            MAX-ACCESS  read-create
            STATUS  current
            DESCRIPTION
                "QoS Policy name."
            ::= { qos2SetTable 1 }

--xxx.100.27.1.16.2
        qos2SetClassMapName OBJECT-TYPE
            SYNTAX  DisplayString (SIZE(1..32))
            MAX-ACCESS  read-create
            STATUS  current
            DESCRIPTION
                "QoS class map name."
            ::= { qos2SetTable 2 }
            
--xxx.100.27.1.16.3
        qos2SetType OBJECT-TYPE
            SYNTAX  INTEGER
            	{
            	    	dscp(1),
               		precedence(2),
                	internal-priority(3),  
                	drop-precedence(4),                	            		
               		nextHop(5),          		
               		v6nextHop(6),
               		cos(7)          	
            	}
            MAX-ACCESS  read-create
            STATUS  current
            DESCRIPTION
                "qos2SetType range:1,2,3,4,5,6
                1   dscp         	Set IP DSCP (DiffServ CodePoints);
                2   precedence   	Set IP precedence;
                3   internal-priority   Set internal-priority;
                4   drop-precedence   	Set drop-precedence;
                5   nexthop      	Set IP nexthop;
		6   v6nextHop    	Set IPv6 nexthop;
                7   cos          	Set CoS ."		
            ::= { qos2SetTable 3 } 
            
--xxx.100.27.1.16.4
        qos2SetDscp OBJECT-TYPE
            SYNTAX  INTEGER(0..63)
            MAX-ACCESS  read-create
            STATUS  current
            DESCRIPTION
                "remark dscp for the classified flow."
            ::= { qos2SetTable 4 } 

--xxx.100.27.1.16.5
        qos2SetPrecedence OBJECT-TYPE
            SYNTAX  INTEGER(0..7)
            MAX-ACCESS  read-create
            STATUS  current
            DESCRIPTION
                "remark ip precedence for classified flow."
            ::= { qos2SetTable 5 }
            
--xxx.100.27.1.16.6
        qos2SetInternalPriority OBJECT-TYPE
            SYNTAX  INTEGER(0..7)
            MAX-ACCESS  read-create
            STATUS  current
            DESCRIPTION
                "remark internal priority for classified flow."
            ::= { qos2SetTable 6 }  
            
--xxx.100.27.1.16.7
        qos2SetDropPrecedence OBJECT-TYPE
            SYNTAX  INTEGER(0..2)
            MAX-ACCESS  read-create
            STATUS  current
            DESCRIPTION
                "remark drop precedence for classified flow."
            ::= { qos2SetTable 7 }                       

--xxx.100.27.1.16.8
        qos2SetDefaultPBR OBJECT-TYPE
            SYNTAX  INTEGER(0..1)
            MAX-ACCESS  read-create
            STATUS  current
            DESCRIPTION
                "0:no set default PBR for classified flow;
                 1:set default PBR for classified flow."
            ::= { qos2SetTable 8 } 
            
--xxx.100.27.1.16.9
        qos2SetVrf OBJECT-TYPE
            SYNTAX  INTEGER(0..252)
            MAX-ACCESS  read-create
            STATUS  current
            DESCRIPTION
                "set vrf value for classified flow."
            ::= { qos2SetTable 9 }              
                         
--xxx.100.27.1.16.10
        qos2SetnextHop OBJECT-TYPE
            SYNTAX  IpAddress
            MAX-ACCESS  read-create
            STATUS  current
            DESCRIPTION
                "set nexthop for classified flow."
            ::= { qos2SetTable 10 }                        
            
--xxx.100.11.1.16.11
        qos2Setv6nextHop OBJECT-TYPE
            SYNTAX  DisplayString
            MAX-ACCESS  read-create
            STATUS  current
            DESCRIPTION
                "set IPv6 nexthop for classified flow"
            ::= { qos2SetTable 11 }

--xxx.100.27.1.16.12
        qos2SetCos OBJECT-TYPE
            SYNTAX  INTEGER(0..7)
            MAX-ACCESS  read-create
            STATUS  current
            DESCRIPTION
                "remark cos for classified flow"
            ::= { qos2SetTable 12 } 
                      

--xxx.100.27.1.16.13
        qos2SetStatus OBJECT-TYPE
            SYNTAX  INTEGER
            	    {
               		active(1),
               		destroy(2)
            	    }
            MAX-ACCESS  read-create
            STATUS  current
            DESCRIPTION
                " Setting it to  active(1) to creates an entry,setting it to destroy(2) to destroy an entry."
            ::= { qos2SetTable 13 } 
	                                                                     
--********************************************************************************************************
--******************************************************************************************************** 
-- (xxx.100.28)   dot1xMgt group

--********************************************************************************************************      

mabOnlineUserTable OBJECT-TYPE
        SYNTAX      SEQUENCE OF MabOnlineUserEntry
        MAX-ACCESS  not-accessible
        STATUS      current
        DESCRIPTION "Show the information of MAB users."
        ::= { dot1xMgt  1 }

mabOnlineUserEntry OBJECT-TYPE
        SYNTAX  MabOnlineUserEntry
        MAX-ACCESS  not-accessible
        STATUS  current
        DESCRIPTION  ""
        INDEX   { mabOnlineUserIndex }
        ::= { mabOnlineUserTable 1 } 

       MabOnlineUserEntry
        ::= SEQUENCE
            {
            	  mabOnlineUserIndex		INTEGER,
                mabOnlineUserMac		  DisplayString,          
                mabOnlineUserName		DisplayString,	
                mabOnlineUserPort		DisplayString,                                     
                mabOnlineUserState	  DisplayString       
            }
            
mabOnlineUserIndex OBJECT-TYPE
        SYNTAX      INTEGER
        MAX-ACCESS  not-accessible
        STATUS      current
        DESCRIPTION "The index of MAB user."
        ::= { mabOnlineUserEntry 1 }
        
mabOnlineUserMac OBJECT-TYPE
        SYNTAX      DisplayString (SIZE(17))
        MAX-ACCESS  read-only
        STATUS      current
        DESCRIPTION "The mac of MAB user."
        ::= { mabOnlineUserEntry 2 }  
        
mabOnlineUserName OBJECT-TYPE
        SYNTAX      DisplayString (SIZE(1..32))
        MAX-ACCESS  read-only
        STATUS      current
        DESCRIPTION "The username of MAB user."
        ::= { mabOnlineUserEntry 3 }  
        
mabOnlineUserState OBJECT-TYPE
        SYNTAX      DisplayString (SIZE(1..18))
        MAX-ACCESS  read-only
        STATUS      current
        DESCRIPTION "The state of MAB user."
        ::= { mabOnlineUserEntry 5 }
        
mabOnlineUserPort OBJECT-TYPE
        SYNTAX      DisplayString (SIZE(1..14))
        MAX-ACCESS  read-only
        STATUS      current
        DESCRIPTION "The port for MAB user."
        ::= { mabOnlineUserEntry 4 }  
        
mabSetUserOffline          OBJECT-TYPE
        SYNTAX      DisplayString (SIZE(17))      
        MAX-ACCESS  read-write
        STATUS      current
        DESCRIPTION "The mac of user offline."
        ::= { dot1xMgt  2 }    
               
dot1xOnlineUserTable OBJECT-TYPE
        SYNTAX      SEQUENCE OF Dot1xOnlineUserEntry
        MAX-ACCESS  not-accessible
        STATUS      current
        DESCRIPTION "Show the information of dot1x users."
        ::= { dot1xMgt  3 }

dot1xOnlineUserEntry OBJECT-TYPE
        SYNTAX  Dot1xOnlineUserEntry
        MAX-ACCESS  not-accessible
        STATUS  current
        DESCRIPTION  ""
        INDEX   { dot1xOnlineUserIndex }
        ::= { dot1xOnlineUserTable 1 } 

       Dot1xOnlineUserEntry
        ::= SEQUENCE
            {
            	  dot1xOnlineUserIndex		INTEGER,
                dot1xOnlineUserMac		  DisplayString, 
                dot1xOnlineUserName		  DisplayString,                       	
                dot1xOnlineUserPort		DisplayString,
                dot1xOnlineUserPortVlanid		INTEGER,
                dot1xOnlineUserPortMethod  DisplayString,
                dot1xOnlineUserPortControl DisplayString,                                                    
                dot1xOnlineUserState	  DisplayString       
            }
            
dot1xOnlineUserIndex OBJECT-TYPE
        SYNTAX      INTEGER
        MAX-ACCESS  not-accessible
        STATUS      current
        DESCRIPTION "The index of dot1x user."
        ::= { dot1xOnlineUserEntry 1 }
        
dot1xOnlineUserMac OBJECT-TYPE
        SYNTAX      DisplayString (SIZE(17))
        MAX-ACCESS  read-only
        STATUS      current
        DESCRIPTION "The mac of dot1x user."
        ::= { dot1xOnlineUserEntry 2 }  
        
dot1xOnlineUserName OBJECT-TYPE
        SYNTAX      DisplayString (SIZE(1..128))
        MAX-ACCESS  read-only
        STATUS      current
        DESCRIPTION "The name of dot1x user."
        ::= { dot1xOnlineUserEntry 3 }          
        
dot1xOnlineUserPort OBJECT-TYPE
        SYNTAX      DisplayString (SIZE(1..16))
        MAX-ACCESS  read-only
        STATUS      current
        DESCRIPTION "The port for dot1x user."
        ::= { dot1xOnlineUserEntry 4 }  
        
dot1xOnlineUserPortVlanid OBJECT-TYPE
        SYNTAX      INTEGER
        MAX-ACCESS  read-only
        STATUS      current
        DESCRIPTION "The vlan id of dot1x user."
        ::= { dot1xOnlineUserEntry 5 }
        
dot1xOnlineUserPortMethod OBJECT-TYPE
        SYNTAX      DisplayString (SIZE(1..20))
        MAX-ACCESS  read-only
        STATUS      current
        DESCRIPTION "The port method dot1x user."
        ::= { dot1xOnlineUserEntry 6 }    
        
dot1xOnlineUserPortControl OBJECT-TYPE
        SYNTAX      DisplayString (SIZE(1..20))
        MAX-ACCESS  read-only
        STATUS      current
        DESCRIPTION "The port control for dot1x user."
        ::= { dot1xOnlineUserEntry 7 }                  
                              
dot1xOnlineUserState OBJECT-TYPE
        SYNTAX      DisplayString (SIZE(1..16))
        MAX-ACCESS  read-only
        STATUS      current
        DESCRIPTION "The state of dot1x user."
        ::= { dot1xOnlineUserEntry 8 }       
        
dot1xSetUserOffline          OBJECT-TYPE
        SYNTAX      DisplayString (SIZE(17))      
        MAX-ACCESS  read-write
        STATUS      current
        DESCRIPTION "The mac of user offline."
        ::= { dot1xMgt  4 }                
       
--********************************************************************************************************
--******************************************************************************************************** 
--xxx.100.29.1 PortMacCountLimit 

portMacCountLimitTable OBJECT-TYPE
    SYNTAX     SEQUENCE OF PortMacCountLimitEntry
    MAX-ACCESS not-accessible
    STATUS     current
    DESCRIPTION
           "The Port Mac Count Limit information table."
    ::= { portMacCountLimit 1 }
    
--xxx.100.29.1.1
portMacCountLimitEntry OBJECT-TYPE
    SYNTAX     PortMacCountLimitEntry
    MAX-ACCESS not-accessible
    STATUS     current
    DESCRIPTION
            "The index of this table is port index."
    INDEX      { portMacCountLimitPortIndex }
    ::= { portMacCountLimitTable 1 }

PortMacCountLimitEntry
        ::= SEQUENCE
            {
                portMacCountLimitPortIndex      INTEGER,
                portMacCountLimitConfigNum      INTEGER,
                portMacCountLimitCurNum		    INTEGER,
				        portMacCountLimitDisable		INTEGER,
				        portMacCountLimitViolationMode  INTEGER,
				        portMacCountLimitShutRecoveryTime INTEGER
            }
       
--xxx.100.29.1.1.1
portMacCountLimitPortIndex  OBJECT-TYPE
            SYNTAX      INTEGER 
            MAX-ACCESS  read-only
            STATUS      current
            DESCRIPTION
                "Port Index."
            ::= { portMacCountLimitEntry 1 }

--xxx.100.29.1.1.2
portMacCountLimitConfigNum   OBJECT-TYPE
            SYNTAX      INTEGER(1..4096) 
            MAX-ACCESS  read-create
            STATUS      current
            DESCRIPTION
                "Configration of the maxmum dynamic mac can be learned on the port."
            ::= { portMacCountLimitEntry 2}            
                    
--xxx.100.29.1.1.3
portMacCountLimitCurNum OBJECT-TYPE
            SYNTAX      INTEGER    
            MAX-ACCESS  read-only
            STATUS      current
            DESCRIPTION
                "The current number of the dynamic mac learned on the port."
            ::= { portMacCountLimitEntry 3 }  
			
--xxx.100.29.1.1.4
portMacCountLimitDisable OBJECT-TYPE
            SYNTAX      INTEGER   
						{
						disable(1),
                                                not-disable(0)
						}			
            MAX-ACCESS  read-create
            STATUS      current
            DESCRIPTION
                "The disable state of mac count limit on the port.the disable state can be set,but enable state is not"
            ::= { portMacCountLimitEntry 4 }  
            
--xxx.100.29.1.1.5
portMacCountLimitViolationMode OBJECT-TYPE
            SYNTAX      INTEGER   
						{
							protect(1),
	            shutdown(2),
	            replace(4)
						}			
            MAX-ACCESS  read-create
            STATUS      current
            DESCRIPTION
                "The violation mode of port mac count reach the threshold.The default mode is protect,if you want to disable violation mode,you can
                config protect mode."
            ::= { portMacCountLimitEntry 5 }  
                                                         
--xxx.100.29.1.1.6
portMacCountLimitShutRecoveryTime OBJECT-TYPE
						SYNTAX      INTEGER (0..3600) 	
            MAX-ACCESS  read-create
            STATUS      current
            DESCRIPTION
                "The recovery time of violation shutdown  mode, the recovery time range is <5-3600>, the value 0 is to cancel recovery time, the value <1-4> is not allowed to config."
            ::= { portMacCountLimitEntry 6 }  
            
			  
--DDM
--***********************************************************************************************************************************
-- xxx.100.30.1

ddmTranscDiagnosisTable OBJECT-TYPE
    SYNTAX     SEQUENCE OF DdmTranscDiagnosisEntry
    MAX-ACCESS not-accessible
    STATUS     current
    DESCRIPTION
            "A list of  ddm transceiver diagnosis information."
    ::= { ddm 1 }
-- xxx.100.30.1.1
		ddmTranscDiagnosisEntry OBJECT-TYPE
		    SYNTAX     DdmTranscDiagnosisEntry
		    MAX-ACCESS not-accessible
		    STATUS     current
		    DESCRIPTION
							"entry for ddm transceiver diagnosis information."
		    INDEX   { ddmDiagnosisIfIndex }
		    ::= { ddmTranscDiagnosisTable 1 }

		DdmTranscDiagnosisEntry ::= SEQUENCE {
		    ddmDiagnosisIfIndex		    INTEGER,
		    ddmDiagnosisTemperature        DisplayString,    
		    ddmDiagTempHighAlarmThreshold   DisplayString,
		    ddmDiagTempLowAlarmThreshold    DisplayString,
		    ddmDiagTempHighWarnThreshold    DisplayString,
		    ddmDiagTempLowWarnThreshold     DisplayString,
		    ddmDiagnosisVoltage		         DisplayString,
		    ddmDiagVoltHighAlarmThreshold   DisplayString,
		    ddmDiagVoltLowAlarmThreshold    DisplayString,
		    ddmDiagVoltHighWarnThreshold    DisplayString,
		    ddmDiagVoltLowWarnThreshold     DisplayString,
		    ddmDiagnosisBias		           DisplayString,
		    ddmDiagBiasHighAlarmThreshold    DisplayString,
		    ddmDiagBiasLowAlarmThreshold     DisplayString,
		    ddmDiagBiasHighWarnThreshold     DisplayString,
		    ddmDiagBiasLowWarnThreshold      DisplayString,
		    ddmDiagnosisRXPower		           DisplayString,
		    ddmDiagRXPowerHighAlarmThreshold   DisplayString,
		    ddmDiagRXPowerLowAlarmThreshold   DisplayString,
		    ddmDiagRXPowerHighWarnThreshold   DisplayString,
		    ddmDiagRXPowerLowWarnThreshold    DisplayString,
		    ddmDiagnosisTXPower		            DisplayString,
		    ddmDiagTXPowerHighAlarmThreshold  DisplayString,
		    ddmDiagTXPowerLowAlarmThreshold   DisplayString,
		    ddmDiagTXPowerHighWarnThreshold   DisplayString,
		    ddmDiagTXPowerLowWarnThreshold    DisplayString
		}
-- xxx.100.30.1.1.1	
    ddmDiagnosisIfIndex   OBJECT-TYPE
			  SYNTAX  INTEGER 
			  MAX-ACCESS  read-only
			  STATUS  current
			  DESCRIPTION
			      "interface NO."
			  ::= { ddmTranscDiagnosisEntry 1 }
-- xxx.100.30.1.1.2
    ddmDiagnosisTemperature   OBJECT-TYPE
			  SYNTAX  DisplayString(SIZE(1..32)) 
			  MAX-ACCESS  read-only
			  STATUS  current
			  DESCRIPTION
			      "current Temperature of the port,and the unit is C."
			  ::= { ddmTranscDiagnosisEntry 2 }
-- xxx.100.30.1.1.3  		  
	ddmDiagTempHighAlarmThreshold   OBJECT-TYPE
			  SYNTAX  DisplayString(SIZE(1..16))  
			  MAX-ACCESS  read-only
			  STATUS  current
			  DESCRIPTION
			      "High alarm threshold of Temperature."
			  ::= { ddmTranscDiagnosisEntry 3 }
			  
	ddmDiagTempLowAlarmThreshold   OBJECT-TYPE
			  SYNTAX  DisplayString(SIZE(1..16))  
			  MAX-ACCESS  read-only
			  STATUS  current
			  DESCRIPTION
			      "Low alarm threshold of Temperature."
			  ::= { ddmTranscDiagnosisEntry 4 }
-- xxx.100.30.1.1.9			  
	 ddmDiagTempHighWarnThreshold   OBJECT-TYPE
			  SYNTAX  DisplayString(SIZE(1..16))  
			  MAX-ACCESS  read-only
			  STATUS  current
			  DESCRIPTION
			      "High warn threshold of Temperature."
			  ::= { ddmTranscDiagnosisEntry 5 }
-- xxx.100.30.1.1.10			  
	 ddmDiagTempLowWarnThreshold   OBJECT-TYPE
			  SYNTAX  DisplayString(SIZE(1..16))  
			  MAX-ACCESS  read-only
			  STATUS  current
			  DESCRIPTION
			      "Low warn threshold of Temperature."
			  ::= { ddmTranscDiagnosisEntry 6}
			  
	ddmDiagnosisVoltage   OBJECT-TYPE
			  SYNTAX  DisplayString(SIZE(1..32))  
			  MAX-ACCESS  read-only
			  STATUS  current
			  DESCRIPTION
			      "voltage of the port,and the unit is V."
			  ::= { ddmTranscDiagnosisEntry 7 }
-- xxx.100.30.1.1.11		  
	 ddmDiagVoltHighAlarmThreshold   OBJECT-TYPE
			  SYNTAX  DisplayString(SIZE(1..16))  
			  MAX-ACCESS  read-only
			  STATUS  current
			  DESCRIPTION
			      "High alarm threshold of Voltage."
			  ::= { ddmTranscDiagnosisEntry 8 }
			  
	ddmDiagVoltLowAlarmThreshold   OBJECT-TYPE
			  SYNTAX  DisplayString(SIZE(1..16))  
			  MAX-ACCESS  read-only
			  STATUS  current
			  DESCRIPTION
			      "Low alarm threshold of Voltage."
			  ::= { ddmTranscDiagnosisEntry 9 }
			  
  ddmDiagVoltHighWarnThreshold   OBJECT-TYPE
			  SYNTAX  DisplayString(SIZE(1..16)) 
			  MAX-ACCESS  read-only
			  STATUS  current
			  DESCRIPTION
			      "High warn threshold of Voltage."
			  ::= { ddmTranscDiagnosisEntry 10}
-- xxx.100.30.1.1.14
    ddmDiagVoltLowWarnThreshold   OBJECT-TYPE
			  SYNTAX  DisplayString(SIZE(1..16))  
			  MAX-ACCESS  read-only
			  STATUS  current
			  DESCRIPTION
			      "Low warn threshold of Voltage."
			  ::= { ddmTranscDiagnosisEntry 11 }
			  
		ddmDiagnosisBias   OBJECT-TYPE
			  SYNTAX  DisplayString(SIZE(1..32))  
			  MAX-ACCESS  read-only
			  STATUS  current
			  DESCRIPTION
			      "bias of the port,the unit is mA."
			  ::= { ddmTranscDiagnosisEntry 12 }
-- xxx.100.30.1.1.15		  
	 ddmDiagBiasHighAlarmThreshold   OBJECT-TYPE
			  SYNTAX  DisplayString(SIZE(1..16))  
			  MAX-ACCESS  read-only
			  STATUS  current
			  DESCRIPTION
			      "High alarm threshold of Bias."
			  ::= { ddmTranscDiagnosisEntry 13 }
-- xxx.100.30.1.1.16			  
	 ddmDiagBiasLowAlarmThreshold   OBJECT-TYPE
			  SYNTAX  DisplayString(SIZE(1..16))  
			  MAX-ACCESS  read-only
			  STATUS  current
			  DESCRIPTION
			      "Low alarm threshold of Bias."
			  ::= { ddmTranscDiagnosisEntry 14 }
-- xxx.100.30.1.1.17		  
	 ddmDiagBiasHighWarnThreshold   OBJECT-TYPE
			  SYNTAX  DisplayString(SIZE(1..16))  
			  MAX-ACCESS  read-only
			  STATUS  current
			  DESCRIPTION
			      "High warn threshold of Bias."
			  ::= { ddmTranscDiagnosisEntry 15 }
			  
	ddmDiagBiasLowWarnThreshold   OBJECT-TYPE
			  SYNTAX  DisplayString(SIZE(1..16))  
			  MAX-ACCESS  read-only
			  STATUS  current
			  DESCRIPTION
			      "Low warn threshold of Bias."
			  ::= { ddmTranscDiagnosisEntry 16 }
			  
	ddmDiagnosisRXPower   OBJECT-TYPE
			  SYNTAX  DisplayString(SIZE(1..32))  
			  MAX-ACCESS  read-only
			  STATUS  current
			  DESCRIPTION
			      "RXPower of the port,and the unit is dBM,if the value of RXPower is infinitesimal,then set it to '-'."
			  ::= { ddmTranscDiagnosisEntry 17 }		
			    
	ddmDiagRXPowerHighAlarmThreshold   OBJECT-TYPE
			  SYNTAX  DisplayString(SIZE(1..16))  
			  MAX-ACCESS  read-only
			  STATUS  current
			  DESCRIPTION
			      "High alarm threshold of RXPower."
			  ::= { ddmTranscDiagnosisEntry 18 }
-- xxx.100.30.1.1.20 			  
	 ddmDiagRXPowerLowAlarmThreshold   OBJECT-TYPE
			  SYNTAX  DisplayString(SIZE(1..16))  
			  MAX-ACCESS  read-only
			  STATUS  current
			  DESCRIPTION
			      "Low alarm threshold of RXPower."
			  ::= { ddmTranscDiagnosisEntry 19 }

-- xxx.100.30.1.1.21		  
	 ddmDiagRXPowerHighWarnThreshold   OBJECT-TYPE
			  SYNTAX  DisplayString(SIZE(1..16))  
			  MAX-ACCESS  read-only
			  STATUS  current
			  DESCRIPTION
			      "High warn threshold of RXPower."
			  ::= { ddmTranscDiagnosisEntry 20 }
-- xxx.100.30.1.1.22		  
	 ddmDiagRXPowerLowWarnThreshold   OBJECT-TYPE
			  SYNTAX  DisplayString(SIZE(1..16))  
			  MAX-ACCESS  read-only
			  STATUS  current
			  DESCRIPTION
			      "Low warn threshold of RXPower."
			  ::= { ddmTranscDiagnosisEntry 21 }
			  
	 ddmDiagnosisTXPower   OBJECT-TYPE
			  SYNTAX  DisplayString(SIZE(1..32))  
			  MAX-ACCESS  read-only
			  STATUS  current
			  DESCRIPTION
			      "TXPower of the port,and the unit is dBM,if the value of TXPoweris infinitesimal,then set it to '-'."
			  ::= { ddmTranscDiagnosisEntry 22 }		  
			  
	ddmDiagTXPowerHighAlarmThreshold   OBJECT-TYPE
			  SYNTAX  DisplayString(SIZE(1..16))  
			  MAX-ACCESS  read-only
			  STATUS  current
			  DESCRIPTION
			      "High alarm threshold of TXPower."
			  ::= { ddmTranscDiagnosisEntry 23 }
			  
	ddmDiagTXPowerLowAlarmThreshold   OBJECT-TYPE
			  SYNTAX  DisplayString(SIZE(1..16))  
			  MAX-ACCESS  read-only
			  STATUS  current
			  DESCRIPTION
			      "k=Low alarm threshold of TXPower."
			  ::= { ddmTranscDiagnosisEntry 24 }
-- xxx.100.30.1.1.25			  
	 ddmDiagTXPowerHighWarnThreshold   OBJECT-TYPE
			  SYNTAX  DisplayString(SIZE(1..16))  
			  MAX-ACCESS  read-only
			  STATUS  current
			  DESCRIPTION
			      "High warn threshold of TXPower."
			  ::= { ddmTranscDiagnosisEntry 25 }
-- xxx.100.30.1.1.26		  
	 ddmDiagTXPowerLowWarnThreshold   OBJECT-TYPE
			  SYNTAX  DisplayString(SIZE(1..16))  
			  MAX-ACCESS  read-only
			  STATUS  current
			  DESCRIPTION
			      "Low warn threshold of TXPower."
			  ::= { ddmTranscDiagnosisEntry 26 }
			  
--  xxx.100.30.2

ddmTranscAlarmTable OBJECT-TYPE
    SYNTAX     SEQUENCE OF DdmTranscAlarmEntry
    MAX-ACCESS not-accessible
    STATUS     current
    DESCRIPTION
            "A list of  ddm transceiver alarm information."
    ::= { ddm 2}
--  xxx.100.30.2.1
		ddmTranscAlarmEntry OBJECT-TYPE
		  SYNTAX     DdmTranscAlarmEntry
		  MAX-ACCESS not-accessible
		  STATUS     current
		  DESCRIPTION
		          "entry for ddm transceiver alarm information."
		  INDEX      { ddmAlarmIfIndex }
		  ::= { ddmTranscAlarmTable 1 }
		
		
		DdmTranscAlarmEntry ::= SEQUENCE {
		  ddmAlarmIfIndex		INTEGER,
		  ddmAlarmInfo          DisplayString
		}
--  xxx.100.30.2.1.1
    ddmAlarmIfIndex   OBJECT-TYPE
			  SYNTAX  INTEGER 
			  MAX-ACCESS  read-only
			  STATUS  current
			  DESCRIPTION
			      "interface NO."
			  ::= { ddmTranscAlarmEntry 1 }
--  xxx.100.30.2.1.2
    ddmAlarmInfo   OBJECT-TYPE
			  SYNTAX  DisplayString(SIZE(0..512)) 
			  MAX-ACCESS  read-only
			  STATUS  current
			  DESCRIPTION
			      "ddm transceiver alarm information."
			  ::= { ddmTranscAlarmEntry 2 }
			  
--  xxx.100.30.3

ddmTranscBasicInfoTable OBJECT-TYPE
    SYNTAX     SEQUENCE OF DdmTranscBasicInfoEntry
    MAX-ACCESS not-accessible
    STATUS     current
    DESCRIPTION
            "Basic info of  ddm transceiver alarm information."
    ::= { ddm 3}
--  xxx.100.30.3.1
ddmTranscBasicInfoEntry OBJECT-TYPE
    SYNTAX     DdmTranscBasicInfoEntry
    MAX-ACCESS not-accessible
    STATUS     current
    DESCRIPTION
	"entry for ddm transceiver basic information."
    INDEX   { ddmAlarmIfIndex }   
    ::= { ddmTranscBasicInfoTable 1 }
		
		
    DdmTranscBasicInfoEntry ::= SEQUENCE { 
        ddmTransSerialIndex       INTEGER,
        ddmTransSerialName        DisplayString,
    	ddmTransSerialNo          DisplayString,
    	ddmTransSerialVendorName  DisplayString,
    	ddmTransSerialModelName   DisplayString,
    	ddmTransSerialTypeName    DisplayString,
	ddmTransSerialBitRate    DisplayString,
	ddmTransSerialWaveLength    DisplayString
    }
 --  xxx.100.30.3.1.1
    ddmTransSerialIndex   OBJECT-TYPE
			  SYNTAX  INTEGER 
			  MAX-ACCESS  read-only
			  STATUS  current
			  DESCRIPTION
			      "ddm Trans Serial Index ."
			  ::= { ddmTranscBasicInfoEntry 1 }
--  xxx.100.30.3.1.2
    ddmTransSerialName   OBJECT-TYPE
			  SYNTAX  DisplayString(SIZE(0..512)) 
			  MAX-ACCESS  read-only
			  STATUS  current
			  DESCRIPTION
			      "ddm Trans Serial Name."
			  ::= { ddmTranscBasicInfoEntry 2 } 
--  xxx.100.30.3.1.3
    ddmTransSerialNo  OBJECT-TYPE
			  SYNTAX  DisplayString(SIZE(0..32)) 
			  MAX-ACCESS  read-only
			  STATUS  current
			  DESCRIPTION
			      "ddm transceiver Serial number."
			  ::= { ddmTranscBasicInfoEntry 3 }           
--  xxx.100.30.3.1.4
    ddmTransSerialVendorName  OBJECT-TYPE
			  SYNTAX  DisplayString(SIZE(0..32)) 
			  MAX-ACCESS  read-only
			  STATUS  current
			  DESCRIPTION
			      "ddm transceiver Vendor Name."
			  ::= { ddmTranscBasicInfoEntry 4 }
--  xxx.100.30.3.1.5
    ddmTransSerialModelName  OBJECT-TYPE
			  SYNTAX  DisplayString(SIZE(0..32)) 
			  MAX-ACCESS  read-only
			  STATUS  current
			  DESCRIPTION
			      "ddm transceiver Model Name:SFP,SFP+,QSFP+,QSFP,XFP,etc."
			  ::= { ddmTranscBasicInfoEntry 5 }
--  xxx.100.30.3.1.6
    ddmTransSerialTypeName  OBJECT-TYPE
			  SYNTAX  DisplayString(SIZE(0..32)) 
			  MAX-ACCESS  read-only
			  STATUS  current
			  DESCRIPTION
			      "ddm transceiver Type Name:1000BASE-T,10GBASE-LR,etc."
			  ::= { ddmTranscBasicInfoEntry 6 }
--  xxx.100.30.3.1.7
    ddmTransSerialBitRate  OBJECT-TYPE
			  SYNTAX  DisplayString(SIZE(0..128)) 
			  MAX-ACCESS  read-only
			  STATUS  current
			  DESCRIPTION
			      "ddm transceiver bit rate:1300Mbit/s,10300Mbit/s,etc."
			  ::= { ddmTranscBasicInfoEntry 7 }
--  xxx.100.30.3.1.8
    ddmTransSerialWaveLength  OBJECT-TYPE
			  SYNTAX  DisplayString(SIZE(0..64)) 
			  MAX-ACCESS  read-only
			  STATUS  current
			  DESCRIPTION
			      "ddm transceiver Wave Length:1310nm,etc."
			  ::= { ddmTranscBasicInfoEntry 8 }

			  
--********************************************************************************************************
--******************************************************************************************************** 
         
-- (xxx.100.31)   priPppoeIaMib
    
--xxx.100.31.1
priPppoeIaGlobalEnable OBJECT-TYPE
    SYNTAX  INTEGER
    {
         disable(0),
         enable(1)
    }   
    MAX-ACCESS  read-write
    STATUS  current
    DESCRIPTION
        " Enable or disable the pppoe-ia function in the switch."
    ::= { priPppoeIaMib  1 }
    
--xxx.100.31.2
priPppoeIaSelfDefinedCircuitID OBJECT-TYPE
    SYNTAX      DisplayString(SIZE(0..128))   
    MAX-ACCESS  read-write
    STATUS  current
    DESCRIPTION
        "If user does not configure the circuit-id of pppoe-ia explicitly on a port, then 
        the user can self-designed format to generate the circuit-id, the format options include
        vlan, port, ID, self-designed string, the circuitId may be only one or any combination of them,
        and is strictly generated according to the sequence of format options, the ID option includes 	
        switch ID and remote-mac, but the user just select only one of them, also In the swtich ID, it 
        includes mac and hostname options, the user just select only one of two, the maximum length 
        of self-designed striing is 64. If user input NULL, then delete the last configuration.
        For example, if select vlan ,ID(swtich-id(mac)), and string 'str' format,
        the user input the string like as 'vlan id swtich-id mac string str'."
    ::= { priPppoeIaMib  2 }
    
--xxx.100.31.3
priPppoeIaTr101CircuitID OBJECT-TYPE
    SYNTAX      DisplayString(SIZE(0..128)) 
    MAX-ACCESS  read-write
    STATUS  current
    DESCRIPTION
        "If user does not configure the circuit-id of pppoe-ia explicitly on a port, then 
        the user can config Tr-101 format to generate the circuit-id, the format like follow
        'identifier-string STRING option (sp|sv|pv|spv) delimiter WORD', the STRING can be any ascii
        except space, and it max length is 47, the WORD must be one in (#|.|,|;|:|/|space). 
        If user input NULL, then delete the last configuration.
        For example, if STRING is switch , option is spv and WORD is '/',
        the user input the string like as 'identifier-string switch option spv delimiter /'."
    ::= { priPppoeIaMib  3 }
    
--xxx.100.31.4
priPppoeIaSelfDefinedRemoteID OBJECT-TYPE
    SYNTAX      DisplayString(SIZE(0..128)) 
    MAX-ACCESS  read-write
    STATUS  current
    DESCRIPTION
        "If user does not configure the remote-id of pppoe-ia explicitly on a port, then 
        the user can self-designed format to generate the remote-id, the format options include
        mac,hostname and self-designed string, the remoteId may be only one or any combination of them,
        and is strictly generated according to the sequence of format options, 
        the maximum length of self-designed striing is 64.
        If user input the NULL, then delete the last configuration.
        For example, if select hostname,mac,and string 'str' format,
        the user input the string like as 'hostname mac string str'."
    ::= { priPppoeIaMib  4 }
    
--xxx.100.31.5
priPppoeIaDelimiter OBJECT-TYPE
    SYNTAX  INTEGER
    {
        default(0),
	pound(1),
        dot(2),
	comma(3),
	semicolon(4),
	colon(5),
        slash(6),
        space(7)
    }   
    MAX-ACCESS  read-write
    STATUS  current
    DESCRIPTION
        " Config pppoe-ia delimiter in circuitId and remoteId.
        Default: the default delimiter of type TR-101 is space, 
        the default delimiter of type self-defined is '\0'"
    ::= { priPppoeIaMib  5 }
    
--xxx.100.31.6
priPppoeIaCircuitIdFormat OBJECT-TYPE
    SYNTAX  INTEGER
    {
        default(0),
        hex(1),
        ascii(2)
    }   
    MAX-ACCESS  read-write
    STATUS  current
    DESCRIPTION
        " Config pppoe-ia circuitId format.
        Default: the default format of the circuitId's mac(if included) is hex, other is ascii"
    ::= { priPppoeIaMib  6 }
    
--xxx.100.31.7
priPppoeIaRemoteIdFormat OBJECT-TYPE
    SYNTAX  INTEGER
    {
        default(0),
        hex(1),
        ascii(2)
    }   
    MAX-ACCESS  read-write
    STATUS  current
    DESCRIPTION
        " Config pppoe-ia remoteId format.
        Default: the default format of the remoteId's mac(if included) is hex, other is ascii"
    ::= { priPppoeIaMib  7 }

--xxx.100.31.8
priPppoeIaTable OBJECT-TYPE
    SYNTAX  SEQUENCE OF PriPppoeIaEntry
    MAX-ACCESS  not-accessible
    STATUS  current
    DESCRIPTION
        " Pppoe-ia configuration in port."
    ::= { priPppoeIaMib   8 }

--xxx.100.31.8.1
    priPppoeIaEntry OBJECT-TYPE
        SYNTAX  PriPppoeIaEntry
        MAX-ACCESS  not-accessible
        STATUS  current
        DESCRIPTION
            " Pppoe-ia configuration in port."
        INDEX   { priPppoeIaPortID }
        ::= { priPppoeIaTable 1 }

    PriPppoeIaEntry ::= SEQUENCE
            {
    	    	priPppoeIaPortID                      INTEGER,            
                priPppoeIaPortEnable                  INTEGER,
                priPppoeIaPortCircuitID               DisplayString,
                priPppoeIaPortRemoteID                DisplayString,
                priPppoeIaPortTrust                   INTEGER,
                priPppoeIaPortVendorTagStrip          INTEGER                                         
            }
            
--xxx.100.31.8.1.1
        priPppoeIaPortID OBJECT-TYPE
            SYNTAX      INTEGER
            MAX-ACCESS  not-accessible
            STATUS      current
            DESCRIPTION "This value is port's ID."
            ::= { priPppoeIaEntry 1 }
                    
--xxx.100.31.8.1.2
        priPppoeIaPortEnable OBJECT-TYPE
            SYNTAX      INTEGER
    	    {
         	disable(0),
         	enable(1)
    	    }             
            MAX-ACCESS  read-write
            STATUS      current
            DESCRIPTION " Enable or disable the pppoe-ia function of the port in the switch. Default:0."
            ::= { priPppoeIaEntry 2 } 
            
--xxx.100.31.8.1.3
        priPppoeIaPortCircuitID OBJECT-TYPE
            SYNTAX      DisplayString(SIZE(0..63))           
            MAX-ACCESS  read-write
            STATUS      current
            DESCRIPTION " Config circuitId for the port. Default:NULL."
            ::= { priPppoeIaEntry 3 } 
            
--xxx.100.31.8.1.4
        priPppoeIaPortRemoteID OBJECT-TYPE
            SYNTAX      DisplayString(SIZE(0..63))            
            MAX-ACCESS  read-write
            STATUS      current
            DESCRIPTION " Config remoteId for the port. Default:NULL."
            ::= { priPppoeIaEntry 4 } 
            
--xxx.100.31.8.1.5
        priPppoeIaPortTrust OBJECT-TYPE
            SYNTAX      INTEGER
    	    {
         	disable(0),
         	enable(1)
    	    }             
            MAX-ACCESS  read-write
            STATUS      current
            DESCRIPTION " Enable or disable the pppoe-ia trust function of the port in the switch. Default:0"
            ::= { priPppoeIaEntry 5 } 
            
--xxx.100.31.8.1.6
        priPppoeIaPortVendorTagStrip OBJECT-TYPE
            SYNTAX      INTEGER
    	    {
         	disable(0),
         	enable(1)
    	    }             
            MAX-ACCESS  read-write
            STATUS      current
            DESCRIPTION " Enable or disable the pppoe-ia vendorTag strip function of the port in the switch. Default:0"
            ::= { priPppoeIaEntry 6 } 
--xxx.100.32.1 PortSecurity 
newPortSecurityTable OBJECT-TYPE
    SYNTAX     SEQUENCE OF NewPortSecurityEntry
    MAX-ACCESS not-accessible
    STATUS     current
    DESCRIPTION
           "The Port Security information table."
    ::= { portSecurity 1 }
--xxx.100.32.1.1
newPortSecurityEntry OBJECT-TYPE
    SYNTAX     NewPortSecurityEntry
    MAX-ACCESS not-accessible
    STATUS     current
    DESCRIPTION
            "The index of this table is port index."
    INDEX      { portSecurityPortIndex }
    ::= { newPortSecurityTable 1 }
NewPortSecurityEntry
        ::= SEQUENCE
            {
                portSecurityPortIndex           INTEGER,
                portSecurityState               INTEGER,
                portSecuritySticky              INTEGER,
                portSecurityMaxMacNum           INTEGER,
                portSecurityCurMacNum           INTEGER,
                portSecurityCfgMacNum           INTEGER,
                portSecurityVioMacNum           INTEGER,
                portSecurityAgingTime           INTEGER,
                portSecurityAgingType           INTEGER,
                portSecurityVioMode             INTEGER,
                portSecurityVioShutRecoveryTime INTEGER,
                portSecurityVioRestrictRecoveryTime INTEGER                                   
            }
--xxx.100.32.1.1.1
portSecurityPortIndex  OBJECT-TYPE
            SYNTAX      INTEGER 
            MAX-ACCESS  read-only
            STATUS      current
            DESCRIPTION
                "Secure Port Index."
            ::= { newPortSecurityEntry 1 }
--xxx.100.32.1.1.2
portSecurityState       OBJECT-TYPE
            SYNTAX      INTEGER   
						{
						enable(1),
            disable(0)
						}			
            MAX-ACCESS  read-create
            STATUS      current
            DESCRIPTION
                "enable or disable port security on this port."
            ::= { newPortSecurityEntry 2 }              
--xxx.100.32.1.1.3
portSecuritySticky       OBJECT-TYPE
            SYNTAX       INTEGER   
						{
						enable(1),
            disable(0)
						}			
            MAX-ACCESS  read-create
            STATUS      current
            DESCRIPTION
                "enable or disable port security sticky on this port.If enable it,the port converts all the dynamic secure 
									MAC addresses, including those that were dynamically learned before sticky learning was enabled,to sticky 
									secure MAC addresses and adds all sticky secure MAC addresses to the running configuration"
            ::= { newPortSecurityEntry 3 }               
--xxx.100.32.1.1.4
portSecurityMaxMacNum   OBJECT-TYPE
            SYNTAX      INTEGER(0..4096) 
            MAX-ACCESS  read-create
            STATUS      current
            DESCRIPTION
                "The maximum number of security mac can be set or learned on the secure port."
            ::= { newPortSecurityEntry 4 }                
--xxx.100.32.1.1.5
portSecurityCurMacNum   OBJECT-TYPE
            SYNTAX      INTEGER(1..4096) 
            MAX-ACCESS  read-only
            STATUS      current
            DESCRIPTION
                "The number of the current security mac on the secure port."
            ::= { newPortSecurityEntry 5 }                
--xxx.100.32.1.1.6
portSecurityCfgMacNum   OBJECT-TYPE
            SYNTAX      INTEGER(1..4096) 
            MAX-ACCESS  read-only
            STATUS      current
            DESCRIPTION
                "The number of security mac can be set on the secure port."
            ::= { newPortSecurityEntry 6 }           
--xxx.100.32.1.1.7
portSecurityVioMacNum   OBJECT-TYPE
            SYNTAX      INTEGER(1..4096) 
            MAX-ACCESS  read-only
            STATUS      current
            DESCRIPTION
                "The violation number of mac received on the secure port."
            ::= { newPortSecurityEntry 7 }       
--xxx.100.32.1.1.8
portSecurityAgingTime   OBJECT-TYPE
            SYNTAX      INTEGER(1..1440) 
            MAX-ACCESS  read-create
            STATUS      current
            DESCRIPTION
                "The aging time for secure address entries on the secure port."
            ::= { newPortSecurityEntry 8 }  
--xxx.100.32.1.1.9
portSecurityAgingType   OBJECT-TYPE
            SYNTAX      INTEGER   
						{
							default(0),
							absolute(1),
							inactivity(2),
							static(4),
							absolute-static (5),
							inactivity-static (6)
						}
            MAX-ACCESS  read-create
            STATUS      current
            DESCRIPTION
                "The aging type for secure address entries on the secure port.If you want to disable inactivity or static aging type,you can config default type."
            ::= { newPortSecurityEntry 9 }                          
--xxx.100.32.1.1.10
portSecurityVioMode   OBJECT-TYPE
            SYNTAX      INTEGER   
						{
							protect(1),
	            restrict(2),
	            shutdown(3)
						}
            MAX-ACCESS  read-create
            STATUS      current
            DESCRIPTION
                "The violation mode of secure port mac count reach the threshold.The default mode is shutdown,if you want to disable violation mode,you can
                config shutdown mode."
            ::= { newPortSecurityEntry 10 }   
--xxx.100.32.1.1.11
portSecurityVioShutRecoveryTime OBJECT-TYPE
						SYNTAX      INTEGER (0..3600) 	
            MAX-ACCESS  read-create
            STATUS      current
            DESCRIPTION
                "The recovery time of violation shutdown  mode, the recovery time range is <5-3600>, the value 0 is to cancel recovery time, the value <1-4> is not allowed to config."
            ::= { newPortSecurityEntry 11 }  	
--xxx.100.32.1.1.12
portSecurityVioRestrictRecoveryTime OBJECT-TYPE
						SYNTAX      INTEGER (0..3600) 	
            MAX-ACCESS  read-create
            STATUS      current
            DESCRIPTION
                "The recovery time of violation restrict  mode, the recovery time range is <5-3600>, the value 0 is to cancel recovery time, the value <1-4> is not allowed to config."
            ::= { newPortSecurityEntry 12 }              
--xxx.100.32.2
portSecurityVlanMaxNumTable OBJECT-TYPE
        SYNTAX      SEQUENCE OF PortSecurityVlanMaxNumEntry
        MAX-ACCESS  not-accessible
        STATUS      current
        DESCRIPTION "Table of maximum mac number with vlan on security port, and the secure port must be on trunk mode."
        ::= { portSecurity 2 }
--xxx.100.32.2.1
portSecurityVlanMaxNumEntry OBJECT-TYPE
        SYNTAX      PortSecurityVlanMaxNumEntry
        MAX-ACCESS  not-accessible
        STATUS      current
        DESCRIPTION "An entry in the port security maximum mac number with vlan table."
        INDEX       { portSecurityPortIndex , portSecurityVlanIndex }
        ::= { portSecurityVlanMaxNumTable 1 }
PortSecurityVlanMaxNumEntry ::= SEQUENCE
{
    portSecurityVlanPortIndex           INTEGER,
    portSecurityVlanIndex               INTEGER,
    portSecurityVlanMaxMacNum           INTEGER,
    portSecurityVlanCurMacNum           INTEGER
}
--xxx.100.32.2.1.1
portSecurityVlanPortIndex OBJECT-TYPE
        SYNTAX      INTEGER
        MAX-ACCESS  read-only
        STATUS      current
        DESCRIPTION "Secure Port Index."
        ::= { portSecurityVlanMaxNumEntry 1 }   
--xxx.100.32.2.1.2
portSecurityVlanIndex OBJECT-TYPE
        SYNTAX      INTEGER(1..4094) 
        MAX-ACCESS  read-only
        STATUS      current
        DESCRIPTION
            "The vlan index on the secure port."
        ::= { portSecurityVlanMaxNumEntry 2 }   
--xxx.100.32.2.1.3
portSecurityVlanMaxMacNum OBJECT-TYPE
        SYNTAX      INTEGER(0..4096) 
        MAX-ACCESS  read-create
        STATUS      current
        DESCRIPTION "The maximum number of security mac can be set or learned in the vlan on the secure port,
        						the maximum range is <1-4096>, the value 0 is to cancel maximum in this vlan,
        						and when you set the maximum number with one vlan the secure port must be on trunk mode."		
        ::= { portSecurityVlanMaxNumEntry 3 }   
--xxx.100.32.2.1.4
portSecurityVlanCurMacNum OBJECT-TYPE
        SYNTAX      INTEGER(1..4096) 
        MAX-ACCESS  read-only
        STATUS      current
        DESCRIPTION "The current number of security mac set or learned in the vlan on the secure port."		
        ::= { portSecurityVlanMaxNumEntry 4 }  
--xxx.100.32.3
portSecurityMacAddressTable OBJECT-TYPE
        SYNTAX      SEQUENCE OF PortSecurityMacAddressEntry
        MAX-ACCESS  not-accessible
        STATUS      current
        DESCRIPTION "Table of mac address on security port."
        ::= { portSecurity 3 }
--xxx.100.32.3.1
portSecurityMacAddressEntry OBJECT-TYPE
        SYNTAX      PortSecurityMacAddressEntry
        MAX-ACCESS  not-accessible
        STATUS      current
        DESCRIPTION "An entry in the port security mac address table."
        INDEX       { portSecurityPortIndex, portSecurityVlanIndex, portSecurityMacAddress}
        ::= { portSecurityMacAddressTable 1 }
PortSecurityMacAddressEntry ::= SEQUENCE
{
    portSecurityMacAddressPortIndex           INTEGER,
    portSecurityMacAddressVlanIndex           INTEGER,
    portSecurityMacAddress                    OCTET STRING,          
    portSecurityMacType                       INTEGER,
    portSecurityMacStatus											INTEGER
}
--xxx.100.32.3.1.1
portSecurityMacAddressPortIndex OBJECT-TYPE
        SYNTAX      INTEGER
        MAX-ACCESS  read-only
        STATUS      current
        DESCRIPTION "Secure Port Index."
        ::= { portSecurityMacAddressEntry 1 }   
--xxx.100.32.3.1.2
portSecurityMacAddressVlanIndex OBJECT-TYPE
        SYNTAX      INTEGER(1..4094) 
        MAX-ACCESS  read-only
        STATUS      current
        DESCRIPTION
            "The vlan index on the secure port.When set mac address,the vlan index must be zero if the port is on access mode."
        ::= { portSecurityMacAddressEntry 2 }   
--xxx.100.32.3.1.3
portSecurityMacAddress OBJECT-TYPE
        SYNTAX      OCTET STRING (SIZE (6)) 
        MAX-ACCESS  read-only
        STATUS      current
        DESCRIPTION "Secure mac address on this secure port"
        ::= { portSecurityMacAddressEntry 3 }  
--xxx.100.32.3.1.4
portSecurityMacType   OBJECT-TYPE
            SYNTAX      INTEGER   
						{
							secured (16),
							secures (32),
							securec (64)
						}
            MAX-ACCESS  read-create
            STATUS      current
            DESCRIPTION
                "The type of mac address on the secure port."
            ::= { portSecurityMacAddressEntry 4 }  
--xxx.100.32.3.1.5      
portSecurityMacStatus   OBJECT-TYPE
            SYNTAX  INTEGER
            	    {
            	    	createAndGo(0),
               		  active(1),
               		  destroy(2)
            	    }
            MAX-ACCESS  read-create
            STATUS  current
            DESCRIPTION
                "Current state of the mac address."
            ::= {portSecurityMacAddressEntry 5} 
--xxx.100.34 porteeeConfig

--***************************************
--prieeePortTable
--***************************************

--xxx.100.34.1
prieeePortTable OBJECT-TYPE
        SYNTAX      SEQUENCE OF PrieeePortEntry
        MAX-ACCESS  not-accessible
        STATUS      current
        DESCRIPTION "A table containing current configuration information
        for each port."
        ::= { prieeePortConfig 1 }

--xxx.100.34.1.1
prieeePortEntry OBJECT-TYPE
        SYNTAX      PrieeePortEntry
        MAX-ACCESS  not-accessible
        STATUS      current
        DESCRIPTION "eee configuration in port"
        INDEX   { portIndex }
        ::= {prieeePortTable 1 }

PrieeePortEntry ::= SEQUENCE
{
    eeePortIndex     INTEGER,
    eeePortStatus    INTEGER
}      
--xxx.100.34.1.1.1
eeePortIndex OBJECT-TYPE
        SYNTAX      INTEGER
        MAX-ACCESS  not-accessible
        STATUS      current
        DESCRIPTION 
            "The eee configuration port index."
        ::= {prieeePortEntry 1 }	
--xxx.100.34.1.1.2
eeePortStatus OBJECT-TYPE
        SYNTAX      INTEGER
 	      {
	      	  enable (1), 
		  disable (0)
	      }        
        MAX-ACCESS  read-write
        STATUS      current
        DESCRIPTION 
        " The eee config. Enable expresses it is turned on, while disable indicates that off."
        ::= { prieeePortEntry 2 } 
        
--xxx.100.35 portRateLimit       
--***************************************
--portRateLimitTable
--***************************************

--xxx.100.35.1  PortRateLimit

portRateLimitTable OBJECT-TYPE
    SYNTAX     SEQUENCE OF PortRateLimitEntry
    MAX-ACCESS not-accessible
    STATUS     current
    DESCRIPTION
           "The Port Receiving Packets Rate Limit information table."
    ::= { portRateLimit 1 }
   
--xxx.100.35.1.1
portRateLimitEntry OBJECT-TYPE
    SYNTAX     PortRateLimitEntry
    MAX-ACCESS not-accessible
    STATUS     current
    DESCRIPTION
            "The index of this table is port index."
    INDEX      { portRateLimitPortIndex }
    ::= { portRateLimitTable 1 }
PortRateLimitEntry
        ::= SEQUENCE
            {
                portRateLimitPortIndex          INTEGER,
                portRateLimitConfigBroadcastNum INTEGER,
                portRateLimitCurBroadcastNum    INTEGER,
                portRateLimitConfigMulticastNum INTEGER,
                portRateLimitCurMulticastNum    INTEGER,
                portRateLimitConfigUnicastNum   INTEGER,
                portRateLimitCurUnicastNum      INTEGER,
                portRateLimitConfigAllNum       INTEGER,
                portRateLimitCurAllNum          INTEGER,
				        portRateLimitPacketsType        INTEGER,
				        portRateLimitViolationMode      INTEGER,
				        portRateLimitShutRecoveryTime   INTEGER
            }
       
--xxx.100.35.1.1.1
portRateLimitPortIndex  OBJECT-TYPE
            SYNTAX      INTEGER 
            MAX-ACCESS  read-only
            STATUS      current
            DESCRIPTION
                "Port Index."
            ::= { portRateLimitEntry 1 }

--xxx.100.35.1.1.2
portRateLimitConfigBroadcastNum   OBJECT-TYPE
            SYNTAX      INTEGER(0..2000000)
            MAX-ACCESS  read-create
            STATUS      current
            DESCRIPTION
                "Configration of the max receiving rate of broadcast packets on the port,the value range is <200-2000000>.
                The value 0 means disable the rate limit of broadcast packets.
                the value <1-199> is not allowed to config."
            ::= { portRateLimitEntry 2} 
            
--xxx.100.35.1.1.3
portRateLimitCurBroadcastNum OBJECT-TYPE
            SYNTAX      INTEGER    
            MAX-ACCESS  read-only
            STATUS      current
            DESCRIPTION
                "The current receiving rate of broadcast packets on the port."
            ::= { portRateLimitEntry 3 }           

--xxx.100.35.1.1.4
portRateLimitConfigMulticastNum   OBJECT-TYPE
            SYNTAX      INTEGER(0..2000000)
            MAX-ACCESS  read-create
            STATUS      current
            DESCRIPTION
                "Configration of the max receiving rate of multicast packets on the port,the value range is <200-2000000>.
                The value 0 means  disable the rate limit of multicast packets.
                the value <1-199> is not allowed to config."
            ::= { portRateLimitEntry 4}

--xxx.100.35.1.1.5
portRateLimitCurMulticastNum OBJECT-TYPE
            SYNTAX      INTEGER    
            MAX-ACCESS  read-only
            STATUS      current
            DESCRIPTION
                "The current receiving rate of Multicast packets on the port."
            ::= { portRateLimitEntry 5 }
                        
--xxx.100.35.1.1.6
portRateLimitConfigUnicastNum   OBJECT-TYPE
            SYNTAX      INTEGER(0..2000000)
            MAX-ACCESS  read-create
            STATUS      current
            DESCRIPTION
                "Configration of the max receiving rate of unicast packets on the port,the value range is <200-2000000>.
                The value 0 means disable the rate limit of unicast packets.
                 the value <1-199> is not allowed to config."
            ::= { portRateLimitEntry 6}
            
--xxx.100.35.1.1.7
portRateLimitCurUnicastNum OBJECT-TYPE
            SYNTAX      INTEGER    
            MAX-ACCESS  read-only
            STATUS      current
            DESCRIPTION
                "The current receiving rate of unicast packets on the port."
            ::= { portRateLimitEntry 7 }

--xxx.100.35.1.1.8
portRateLimitConfigAllNum   OBJECT-TYPE
            SYNTAX      INTEGER(0..2000000)
            MAX-ACCESS  read-create
            STATUS      current
            DESCRIPTION
                "Configration of the max receiving rate of all packets on the port,the value range is <200-2000000>.
                The value 0 means disable the rate limit of all packets.
                 the value <1-199> is not allowed to config."
            ::= { portRateLimitEntry 8}
                                                      
--xxx.100.35.1.1.9
portRateLimitCurAllNum OBJECT-TYPE
            SYNTAX      INTEGER    
            MAX-ACCESS  read-only
            STATUS      current
            DESCRIPTION
                "The current receiving rate of all packets on the port."
            ::= { portRateLimitEntry 9 }   
                       
--xxx.100.35.1.1.10
portRateLimitPacketsType OBJECT-TYPE
            SYNTAX      INTEGER   	
            MAX-ACCESS  read-only
            STATUS      current
            DESCRIPTION
                "Which type of receiving packets that rate limit is set.
                0:none, 1:broadcast, 2:multicast, 3:unicast, 4:all,
                5:broadcast+multicast, 6:broadcast+unicast, 7:multicast+unicast.
                8:broadcast+all, 9:multicast+all, 10:unicast+all, 11:broadcast+multicast+all,
                12:broadcast+unicast+all, 13:multicast+unicast+all, 14:broadcast+multicast+unicast,
                15:broadcast+multicast+unicast+all"
            ::= { portRateLimitEntry 10 }
                                                         
--xxx.100.35.1.1.11
portRateLimitViolationMode OBJECT-TYPE
            SYNTAX      INTEGER   
						{
              nocontrol(0),
	            shutdown(1),
	            block(2)
						}			
            MAX-ACCESS  read-create
            STATUS      current
            DESCRIPTION
                "The violation mode of port receiving packets rate reach the threshold.The default mode is no violation actions."
            ::= { portRateLimitEntry 11 }  
                                                         
--xxx.100.35.1.1.12
portRateLimitShutRecoveryTime OBJECT-TYPE
						SYNTAX      INTEGER (0..86400) 	
            MAX-ACCESS  read-create
            STATUS      current
            DESCRIPTION
                "The recovery time of violation shutdown  mode, the recovery time range is <0-86400>,
                 the value 0 means the port cann't be recovery forever, the default value is 300."
            ::= { portRateLimitEntry 12 }
            

--********************************************************************************************************
--******************************************************************************************************** 

--xxx.100.36  macBlackholeConfig

--***************************************
--macBlackholeTable
--***************************************            
--xxx.100.36.1
macBlackholeTable OBJECT-TYPE
        SYNTAX      SEQUENCE OF MacBlackholeEntry
        MAX-ACCESS  not-accessible
        STATUS      current
        DESCRIPTION "A table containing current configuration information for each mac in vlan`s status."
        ::= { macBlackholeConfig 1 }

--xxx.100.36.1.1
macBlackholeEntry OBJECT-TYPE
        SYNTAX      MacBlackholeEntry
        MAX-ACCESS  not-accessible
        STATUS      current
        DESCRIPTION "Thie entry is control the mac add to blackhole or delete from blackhole."
        INDEX   { macAddressInVlanID, macAddress }
        ::= { macBlackholeTable 1 }

MacBlackholeEntry ::= SEQUENCE
{
    macAddressInVlanID          INTEGER,
    macAddress                  OCTET STRING,
    macType                     INTEGER,
    macStatus                   INTEGER
}

        
--xxx.100.36.1.1.1
macAddressInVlanID OBJECT-TYPE
        SYNTAX      INTEGER (1..4094)
        MAX-ACCESS  not-accessible
        STATUS      current
        DESCRIPTION "This value is the mac address in vlan."
        ::= { macBlackholeEntry 1 }

--xxx.100.36.1.1.2
macAddress OBJECT-TYPE
        SYNTAX      OCTET STRING (SIZE (6))
        MAX-ACCESS  not-accessible
        STATUS      current
        DESCRIPTION "This value is mac address."
        ::= { macBlackholeEntry 2 }

--xxx.100.36.1.1.3
macType OBJECT-TYPE
        SYNTAX      INTEGER 
        	{      
                   both(0),
                   source(1),
                   destination(2)    		
    		}
        MAX-ACCESS  read-create
        STATUS      current
        DESCRIPTION "Control the mac from both(0)/source(1)/destination(2).Default both(0)."
        ::= { macBlackholeEntry 3 }

--xxx.100.36.1.1.4
macStatus OBJECT-TYPE
    SYNTAX      INTEGER
    		{
               	   creat(0),
               	   active(1),
               	   destroy(2)    		
    		}
    MAX-ACCESS  read-create
    STATUS      current
    DESCRIPTION
        "creat(0) the mac to blackhole,or destroy(2) the mac from blackhole.active(1)the mac in blackhole"
    ::= { macBlackholeEntry 4 }  
    
    
 
--********************************************************************************************************
--******************************************************************************************************** 
--xxx.100.37  priCable
--***************************************
--cableTable
--***************************************   
--PriCableEntry
--***************************************      
--xxx.100.37.1
priCableTable OBJECT-TYPE
    SYNTAX  SEQUENCE OF PriCableEntry
    MAX-ACCESS  not-accessible
    STATUS  current
    DESCRIPTION
        " A list of port entries."
    ::= { priCable   1 }

--xxx.100.37.1.1
    priCableEntry OBJECT-TYPE
        SYNTAX  PriCableEntry
        MAX-ACCESS  not-accessible
        STATUS  current
        DESCRIPTION
            " A port entry containing port information, 
            status, and control."
        INDEX   { cableLengthInfo }
        ::= { priCableTable 1 }

    PriCableEntry
        ::= SEQUENCE
            {
                cableLengthInfo               DisplayString                   
            }

--xxx.100.37.1.1.1
        cableLengthInfo OBJECT-TYPE
            SYNTAX  DisplayString (SIZE(0..32))
            MAX-ACCESS  read-only
            STATUS  current
            DESCRIPTION
                "Cable Length Info."
            ::= {priCableEntry 1 } 
-----------------------------------------------------------------------------------
--weiyya 2014.12.30
--xxx.100.38 priMrppRing       
--***************************************
--priMrppRingTable
--***************************************
 
--xxx.100.38.1  priMrppRing

priMrppRingTable OBJECT-TYPE
    SYNTAX     SEQUENCE OF PriMrppRingEntry
    MAX-ACCESS not-accessible
    STATUS     current
    DESCRIPTION
           "The MRPP Ring information table."
    ::= { priMrppRing 1 }
   
--xxx.100.38.1.1
priMrppRingEntry OBJECT-TYPE
    SYNTAX     PriMrppRingEntry
    MAX-ACCESS not-accessible
    STATUS     current
    DESCRIPTION
            "The index of this table is RING index."
    INDEX      { mrppRingIndex }
    ::= { priMrppRingTable 1 }
PriMrppRingEntry
        ::= SEQUENCE
            {
                mrppRingIndex                      INTEGER,
                mrppRingNodeMode                   INTEGER,
                mrppRingNodeState                  INTEGER,
                mrppRingStatus		               INTEGER,
                mrppRingPriPortName                OCTET STRING,
                mrppRingPriPortBlockState          INTEGER,
                mrppRingSecPortName                OCTET STRING,
                mrppRingSecPortBlockState          INTEGER
            }
       
--xxx.100.38.1.1.1
mrppRingIndex  OBJECT-TYPE
            SYNTAX      INTEGER 
            MAX-ACCESS  read-only
            STATUS      current
            DESCRIPTION
                "mrpp ring Index<1-4096>."
            ::= { priMrppRingEntry 1 } 
--xxx.100.38.1.1.2
mrppRingNodeMode   OBJECT-TYPE
            SYNTAX      INTEGER
            MAX-ACCESS  read-only
            STATUS      current
            DESCRIPTION
                "mrpp ring node mode:MASTER:1,TRANSIT:0."
            ::= { priMrppRingEntry 2} 
--xxx.100.38.1.1.3
mrppRingNodeState   OBJECT-TYPE
            SYNTAX      INTEGER
            MAX-ACCESS  read-only
            STATUS      current
            DESCRIPTION
                "mrpp ring node state:
                 IDLE:            0,
                 COMPLETE:        1,
                 FAILED:          2,
                 LINKS_UP:        3,
                 LINKS_DOWN:      4,
                 PRE_FORWARDING:  5."
            ::= { priMrppRingEntry 3} 
--xxx.100.38.1.1.4
mrppRingStatus   OBJECT-TYPE
            SYNTAX      INTEGER
            MAX-ACCESS  read-only
            STATUS      current
            DESCRIPTION
                "mrpp ring status:enable:1,disable:0."
            ::= { priMrppRingEntry 4}             

--xxx.100.38.1.1.5
mrppRingPriPortName   OBJECT-TYPE
            SYNTAX      DisplayString
            MAX-ACCESS  read-only
            STATUS      current
            DESCRIPTION
                "ring's traffic primary port name."
            ::= { priMrppRingEntry 5} 
            
--xxx.100.38.1.1.6
mrppRingPriPortBlockState OBJECT-TYPE
            SYNTAX      INTEGER    
            MAX-ACCESS  read-only
            STATUS      current
            DESCRIPTION
                "ring's traffic primary port block state:BLOCK:1,UNBLOCK:0."
            ::= { priMrppRingEntry 6 }           

--xxx.100.38.1.1.7
mrppRingSecPortName   OBJECT-TYPE
            SYNTAX      DisplayString
            MAX-ACCESS  read-only
            STATUS      current
            DESCRIPTION
                "ring's traffic secondary port name."
            ::= { priMrppRingEntry 7} 
            
--xxx.100.38.1.1.8
mrppRingSecPortBlockState   OBJECT-TYPE
            SYNTAX      INTEGER
            MAX-ACCESS  read-only
            STATUS      current
            DESCRIPTION
                "ring's traffic secondary port block state:BLOCK:1,UNBLOCK:0."
            ::= { priMrppRingEntry 8}
                                        
--weiyya end 
--********************************************************************************************************  
--xxx.100.39  erpsMgt
--xxx.100.39.1
erpsTcnPropagationConfig OBJECT-TYPE
        SYNTAX  INTEGER
               {
                none(0),
                erps(1),
                stp (2)
               }
        MAX-ACCESS  read-write
        STATUS      current
        DESCRIPTION "Config Topology change propagation type."
        ::= { erpsMgt 1 }    
--********************************************************************************************************
--xxx.100.39.2
erpsRingConfigTable OBJECT-TYPE
    SYNTAX     SEQUENCE OF ErpsRingConfigEntry
    MAX-ACCESS not-accessible
    STATUS     current
    DESCRIPTION
           "Erps Ring configration table."
    ::= { erpsMgt 2 }
--xxx.100.39.2.1    
erpsRingConfigEntry OBJECT-TYPE
    SYNTAX     ErpsRingConfigEntry
    MAX-ACCESS not-accessible
    STATUS     current
    DESCRIPTION
            "Erps Ring configration entry."
    INDEX      {erpsRingNameIndex}
    ::= { erpsRingConfigTable 1 }

ErpsRingConfigEntry
        ::= SEQUENCE
            {
                erpsRingNameIndex        INTEGER,
                erpsRingName             DisplayString,       
               
                erpsVersion	             INTEGER,
                erpsOpenRing             INTEGER,
                erpsRapsVirtualChannel   INTEGER,
                erpsRingPort0            DisplayString,
                erpsRingPort0Index       INTEGER,
                erpsRingPort1ExistFlag    INTEGER,
				erpsRingPort1            DisplayString,
                erpsRingPort1Index       INTEGER,
                erpsRingRowStatus        INTEGER,
                erpsTrapEnabled          INTEGER,
		erpsLogEnabled          INTEGER 
            }
--xxx.100.39.2.1.1
erpsRingNameIndex  OBJECT-TYPE
            SYNTAX      INTEGER 
            MAX-ACCESS  read-only
            STATUS      current
            DESCRIPTION
                "erps ring name index, the max number is 32."
           ::= { erpsRingConfigEntry 1}
--xxx.100.39.2.1.2        
erpsRingName  OBJECT-TYPE
            SYNTAX      DisplayString(SIZE (1..64))    
            MAX-ACCESS  read-write
            STATUS      current
            DESCRIPTION
                "erps ring name."
            ::= { erpsRingConfigEntry 2}
-- xxx.100.39.2.1.3       
erpsVersion   OBJECT-TYPE
            SYNTAX      INTEGER
            {
                default(0),
                v1(1),
                v2(2)
            } 
            MAX-ACCESS  read-write
            STATUS      current
            DESCRIPTION
                "Version Ethernet ring node running ITU-T G.8032."
            ::= { erpsRingConfigEntry 3}
--xxx.100.39.2.1.4        
erpsOpenRing   OBJECT-TYPE
            SYNTAX      INTEGER
            {
                none-open(0),
                open(1)
            } 
            MAX-ACCESS  read-write
            STATUS      current
            DESCRIPTION
                "set Erps ring topolagy type ."
            ::= { erpsRingConfigEntry 4}
--xxx.100.39.2.1.5        
erpsRapsVirtualChannel   OBJECT-TYPE
            SYNTAX      INTEGER
            {
                without(0),
                with(1)
            } 
            MAX-ACCESS  read-write
            STATUS      current
            DESCRIPTION
                "R-APS virtual channel configuration ."
            ::= { erpsRingConfigEntry 5}            
--xxx.100.39.2.1.6        
erpsRingPort0   OBJECT-TYPE
            SYNTAX      DisplayString(SIZE (1..64))
            MAX-ACCESS  read-write
            STATUS      current
            DESCRIPTION
                "ERPS ring's member port0 ."
            ::= { erpsRingConfigEntry 6} 
--xxx.100.39.2.1.7        
erpsRingPort0Index   OBJECT-TYPE
            SYNTAX      INTEGER
            MAX-ACCESS  read-only
            STATUS      current
            DESCRIPTION
                "ERPS ring's member port0 index ."
            ::= { erpsRingConfigEntry 7}   
--xxx.100.39.2.1.8        
erpsRingPort1ExistFlag   OBJECT-TYPE
            SYNTAX      INTEGER 
			{
	            none(0),				
				not-none(1)
            }
            MAX-ACCESS  read-write
            STATUS      current
            DESCRIPTION
                "ERPS ring's member port1 whether has been set none; 
				 can not be set alone,must be set with erpsRingPort0 together."
            ::= { erpsRingConfigEntry 8}   			
--xxx.100.39.2.1.9        
erpsRingPort1   OBJECT-TYPE
            SYNTAX      DisplayString(SIZE (1..64))
            MAX-ACCESS  read-write
            STATUS      current
            DESCRIPTION
                "ERPS ring's member port1 ."
            ::= { erpsRingConfigEntry 9} 
--xxx.100.39.2.1.10        
erpsRingPort1Index   OBJECT-TYPE
            SYNTAX      INTEGER
            MAX-ACCESS  read-only
            STATUS      current
            DESCRIPTION
                "ERPS ring's member port1 index ."
            ::= { erpsRingConfigEntry 10}             
--xxx.100.39.2.1.11        
erpsRingRowStatus   OBJECT-TYPE
            SYNTAX      INTEGER
            {
	            unset(0),				
				set(1)
            }
            MAX-ACCESS  read-write
            STATUS      current
            DESCRIPTION
                "ERPS ring's row status ."
            ::= { erpsRingConfigEntry 11}  
--xxx.100.39.2.1.12        
erpsTrapEnabled  OBJECT-TYPE
            SYNTAX      INTEGER
            {
	            unset(0),				
                    set(1)
            }
            MAX-ACCESS  read-write
            STATUS      current
            DESCRIPTION
                "ERPS trap configration."
            ::= { erpsRingConfigEntry 12} 
--xxx.100.39.2.1.13        
erpsLogEnabled  OBJECT-TYPE
            SYNTAX      INTEGER
            {
	            unset(0),				
                    set(1)
            }
            MAX-ACCESS  read-write
            STATUS      current
            DESCRIPTION
                "ERPS log configration."
            ::= { erpsRingConfigEntry 13}  	     
--xxx.100.39.3                      
            
erpsInstanceConfigTable OBJECT-TYPE
    SYNTAX     SEQUENCE OF ErpsInstanceConfigEntry
    MAX-ACCESS not-accessible
    STATUS     current
    DESCRIPTION
           "erps Instance configration table."
    ::= { erpsMgt 3 }
--xxx.100.39.3.1    
erpsInstanceConfigEntry OBJECT-TYPE
    SYNTAX     ErpsInstanceConfigEntry
    MAX-ACCESS not-accessible
    STATUS     current
    DESCRIPTION
            "A set of configuration parameters for erps Instance."
    INDEX      {erpsRingNameIndex, erpsInstanceId}
    ::= { erpsInstanceConfigTable 1 } 
    
ErpsInstanceConfigEntry
        ::= SEQUENCE
            {
                --erpsRingName               DisplayString,
		        erpsInstanceId             INTEGER,          
                erpsDescription            DisplayString,
                erpsRingId	               INTEGER,
                erpsRplPort0Role           INTEGER,
                erpsRplPort1Role           INTEGER,
                erpsRevertiveMode          INTEGER,
                erpsGuardTimer             INTEGER,
                erpsHoldoffTimer           INTEGER,
                erpsWtrTimer               INTEGER,
                erpsProtectedInstance      DisplayString,
                erpsRapsMel                INTEGER,
                erpsControlVlan            INTEGER,
                erpsForcedSwitch           INTEGER,
                erpsManualSwitch           INTEGER,
                erpsClearCommand           INTEGER,
                erpsClearPortStatistics    INTEGER,
                erpsInstanceRowStatus      INTEGER  
            } 
 --erpsRingName  OBJECT-TYPE
--            SYNTAX      DisplayString(SIZE (1..64)) 
 --           MAX-ACCESS  not-accessible
 --           STATUS      current
 --           DESCRIPTION
  --              "ERPS Ring Name."
  --          ::= { erpsInstanceConfigEntry 18}           
 --xxx.100.39.3.1.1
erpsInstanceId  OBJECT-TYPE
            SYNTAX      INTEGER    
            MAX-ACCESS  read-only
            STATUS      current
            DESCRIPTION
                "erps instance id.scope:<1-48>"
            ::= { erpsInstanceConfigEntry 1}
--xxx.100.39.3.1.2        
erpsDescription  OBJECT-TYPE
            SYNTAX      DisplayString(SIZE (1..64)) 
            MAX-ACCESS  read-write
            STATUS      current
            DESCRIPTION
                "ERPS instance description."
            ::= { erpsInstanceConfigEntry 2}
--xxx.100.39.3.1.3        
erpsRingId   OBJECT-TYPE
            SYNTAX      INTEGER
            MAX-ACCESS  read-write
            STATUS      current
            DESCRIPTION
                "Set Ring ID that R-APS MAC address included.scope:<1-64>"
            ::= { erpsInstanceConfigEntry 3}
--xxx.100.39.3.1.4        
erpsRplPort0Role   OBJECT-TYPE
            SYNTAX      INTEGER
            {
                default(0),
                owner(1),
                neighbour(2)
            } 
            MAX-ACCESS  read-write
            STATUS      current
            DESCRIPTION
                "Set Ring membor port0's role."
            ::= { erpsInstanceConfigEntry 4}  
--xxx.100.39.3.1.5        
erpsRplPort1Role   OBJECT-TYPE
            SYNTAX      INTEGER
            {
                default(0),
                owner(1),
                neighbour(2)
            } 
            MAX-ACCESS  read-write
            STATUS      current
            DESCRIPTION
                "Set Ring membor port1's role."
            ::= { erpsInstanceConfigEntry 5}

--xxx.100.39.3.1.6        
erpsRevertiveMode   OBJECT-TYPE
            SYNTAX      INTEGER
            {
                default(0),
                non-revertive(1)
            } 
            MAX-ACCESS  read-write
            STATUS      current
            DESCRIPTION
                "Set ERPS Ring working in non-revertive or revertive operation."
            ::= { erpsInstanceConfigEntry 6} 
--xxx.100.39.3.1.7        
erpsGuardTimer   OBJECT-TYPE
            SYNTAX      INTEGER 
            MAX-ACCESS  read-write
            STATUS      current
            DESCRIPTION
                "Guard timer configuration.scope:<1-200>"
            ::= { erpsInstanceConfigEntry 7}            
--xxx.100.39.3.1.8        
erpsHoldoffTimer   OBJECT-TYPE
            SYNTAX      INTEGER 
            MAX-ACCESS  read-write
            STATUS      current
            DESCRIPTION
                "Holdoff timer, scope:<0-10>"
            ::= { erpsInstanceConfigEntry 8}             
--xxx.100.39.3.1.9        
erpsWtrTimer   OBJECT-TYPE
            SYNTAX      INTEGER            
            MAX-ACCESS  read-write
            STATUS      current
            DESCRIPTION
                "Wait To Restore configuration.scope:<1-12>"
            ::= { erpsInstanceConfigEntry 9}             
--xxx.100.39.3.1.10        
erpsProtectedInstance    OBJECT-TYPE
            SYNTAX      DisplayString(SIZE (1..64))             
            MAX-ACCESS  read-write
            STATUS      current
            DESCRIPTION
                "Protection vlan reference MSTP instance configuration"
            ::= { erpsInstanceConfigEntry 10} 
--xxx.100.39.3.1.11        
erpsRapsMel    OBJECT-TYPE
            SYNTAX      INTEGER             
            MAX-ACCESS  read-write
            STATUS      current
            DESCRIPTION
                "R-APS Maintenance Entity Group Level configuration.scope:<0-7>"
            ::= { erpsInstanceConfigEntry 11}   
--xxx.100.39.3.1.12        
erpsControlVlan    OBJECT-TYPE
            SYNTAX      INTEGER             
            MAX-ACCESS  read-write
            STATUS      current
            DESCRIPTION
                "Control vlan configuration"
            ::= { erpsInstanceConfigEntry 12}          
--xxx.100.39.3.1.13        
erpsForcedSwitch    OBJECT-TYPE
            SYNTAX      INTEGER
            {
                default(0),				
		        port0-forced-switch(1),
		        port1-forced-switch(2)
            }             
            MAX-ACCESS  read-write
            STATUS      current
            DESCRIPTION
                "Forces a block on the ring port"
            ::= { erpsInstanceConfigEntry 13}  
--xxx.100.39.3.1.14        
erpsManualSwitch    OBJECT-TYPE
            SYNTAX      INTEGER
            {
                default(0),				
	 	        port0-manual-switch(1),
	         	port1-manual-switch(2)
            }             
            MAX-ACCESS  read-write
            STATUS      current
            DESCRIPTION
                "Forces a block on the ring port in the absence of a failure or FS"
            ::= { erpsInstanceConfigEntry 14} 
--xxx.100.39.3.1.15        
erpsClearCommand    OBJECT-TYPE
            SYNTAX      INTEGER
            {
				clear(1)
            }             
            MAX-ACCESS  read-write
            STATUS      current
            DESCRIPTION
                "Clear an administrative command"
            ::= { erpsInstanceConfigEntry 15}  
--xxx.100.39.3.1.16        
erpsClearPortStatistics    OBJECT-TYPE
            SYNTAX      INTEGER
            {
				clear(1)
            }             
            MAX-ACCESS  read-write
            STATUS      current
            DESCRIPTION
                "Clear an administrative command"
            ::= { erpsInstanceConfigEntry 16}  
--xxx.100.39.3.1.17        
erpsInstanceRowStatus    OBJECT-TYPE
            SYNTAX      INTEGER
            {
                unset(0),				
				set(1)
            }             
            MAX-ACCESS  read-write
            STATUS      current
            DESCRIPTION
                "Clear an administrative command"
            ::= { erpsInstanceConfigEntry 17}          

--xxx.100.39.4
erpsStatus         	                    OBJECT IDENTIFIER ::= { erpsMgt 4 }
--xxx.100.39.4.1
--erpsInstanceStatusTable         	    OBJECT IDENTIFIER ::= { erpsStatus  1 } 
--xxx.100.39.4.2
--erpsPortStatusTable         	        OBJECT IDENTIFIER ::= { erpsStatus  2 } 


--xxx.100.39.4.1                     
erpsInstanceStatusTable OBJECT-TYPE
    SYNTAX     SEQUENCE OF ErpsInstanceStatusEntry
    MAX-ACCESS not-accessible
    STATUS     current
    DESCRIPTION
           "erps Instance status table."
    ::= { erpsStatus 1 }
--xxx.100.39.4.1.1    
erpsInstanceStatusEntry OBJECT-TYPE
    SYNTAX     ErpsInstanceStatusEntry
    MAX-ACCESS not-accessible
    STATUS     current
    DESCRIPTION
            "erps instance status."
    INDEX      {erpsRingNameIndex,erpsInstanceId}
    ::= { erpsInstanceStatusTable 1 } 
    
ErpsInstanceStatusEntry
        ::= SEQUENCE
            {
                erpsActiveStatus             INTEGER,          
                erpsNodeState                INTEGER 
            } 
            
 --xxx.100.39.4.1.1.1
erpsActiveStatus  OBJECT-TYPE
            SYNTAX      INTEGER    
            MAX-ACCESS  read-only
            STATUS      current
            DESCRIPTION
                "erps instance active status."
            ::= { erpsInstanceStatusEntry 1}  
 --xxx.100.39.4.1.1.2
erpsNodeState  OBJECT-TYPE
            SYNTAX      INTEGER    
            MAX-ACCESS  read-only
            STATUS      current
            DESCRIPTION
                "erps instance node state."
            ::= { erpsInstanceStatusEntry 2}

-------------------------------------------
--xxx.100.39.4.2                     
erpsPort0StatusTable OBJECT-TYPE
    SYNTAX     SEQUENCE OF ErpsPort0StatusEntry
    MAX-ACCESS not-accessible
    STATUS     current
    DESCRIPTION
           "erps port status table."
    ::= { erpsStatus 2 }
--xxx.100.39.4.2.1    
erpsPort0StatusEntry OBJECT-TYPE
    SYNTAX     ErpsPort0StatusEntry
    MAX-ACCESS not-accessible
    STATUS     current
    DESCRIPTION
            "erps port0 status."
    INDEX      {erpsRingNameIndex, erpsInstanceId}
    ::= { erpsPort0StatusTable 1 } 
    
ErpsPort0StatusEntry
        ::= SEQUENCE
            {
                erpsPort0Name                  DisplayString,          
                erpsPort0Status                INTEGER,
                erpsPort0SignalStatus          INTEGER,
                erpsPort0RRapsNodeId           DisplayString,
                erpsPort0BPR                   INTEGER
            } 
 --xxx.100.39.4.2.1.1
erpsPort0Name  OBJECT-TYPE
            SYNTAX      DisplayString(SIZE (1..64))    
            MAX-ACCESS  read-only
            STATUS      current
            DESCRIPTION
                "erps port0's name."
            ::= { erpsPort0StatusEntry 1}  
 --xxx.100.39.4.2.1.2
erpsPort0Status  OBJECT-TYPE
            SYNTAX      INTEGER    
            MAX-ACCESS  read-only
            STATUS      current
            DESCRIPTION
                "erps port0's block status."
            ::= { erpsPort0StatusEntry 2}
 --xxx.100.39.4.2.1.3
erpsPort0SignalStatus  OBJECT-TYPE
            SYNTAX      INTEGER    
            MAX-ACCESS  read-only
            STATUS      current
            DESCRIPTION
                "erps port0's siginal status."
            ::= { erpsPort0StatusEntry 3}
 --xxx.100.39.4.2.1.4
erpsPort0RRapsNodeId  OBJECT-TYPE
            SYNTAX      DisplayString(SIZE (1..64))   
            MAX-ACCESS  read-only
            STATUS      current
            DESCRIPTION
                "erps port0's R-APS-NodeId."
            ::= { erpsPort0StatusEntry 4} 
 --xxx.100.39.4.2.1.5
erpsPort0BPR  OBJECT-TYPE
            SYNTAX      INTEGER    
            MAX-ACCESS  read-only
            STATUS      current
            DESCRIPTION
                "erps port0's BPR value."
            ::= { erpsPort0StatusEntry 5}
           
--xxx.100.39.4.3                     
erpsPort1StatusTable OBJECT-TYPE
    SYNTAX     SEQUENCE OF ErpsPort1StatusEntry
    MAX-ACCESS not-accessible
    STATUS     current
    DESCRIPTION
           "erps port1 status table."
    ::= { erpsStatus 3 }
--xxx.100.39.4.3.1    
erpsPort1StatusEntry OBJECT-TYPE
    SYNTAX     ErpsPort1StatusEntry
    MAX-ACCESS not-accessible
    STATUS     current
    DESCRIPTION
            "erps port1 status."
    INDEX      {erpsRingNameIndex, erpsInstanceId}
    ::= { erpsPort1StatusTable 1 } 
    
ErpsPort1StatusEntry
        ::= SEQUENCE
            {
                erpsPort1Name                  DisplayString,          
                erpsPort1Status                INTEGER,
                erpsPort1SignalStatus          INTEGER,
                erpsPort1RRapsNodeId           DisplayString,
                erpsPort1BPR                   INTEGER

            }            
 --xxx.100.39.4.3.1.1
erpsPort1Name  OBJECT-TYPE
            SYNTAX      DisplayString(SIZE (1..64))    
            MAX-ACCESS  read-only
            STATUS      current
            DESCRIPTION
                "erps port1's name."
            ::= { erpsPort1StatusEntry 1}  
 --xxx.100.39.4.3.1.2
erpsPort1Status  OBJECT-TYPE
            SYNTAX      INTEGER    
            MAX-ACCESS  read-only
            STATUS      current
            DESCRIPTION
                "erps port1's block status."
            ::= { erpsPort1StatusEntry 2}
 --xxx.100.39.4.3.1.3
erpsPort1SignalStatus  OBJECT-TYPE
            SYNTAX      INTEGER    
            MAX-ACCESS  read-only
            STATUS      current
            DESCRIPTION
                "erps port1's siginal status."
            ::= { erpsPort1StatusEntry 3}
 --xxx.100.39.4.3.1.4
erpsPort1RRapsNodeId  OBJECT-TYPE
            SYNTAX      DisplayString(SIZE (1..64))   
            MAX-ACCESS  read-only
            STATUS      current
            DESCRIPTION
                "erps port1's R-APS-NodeId."
            ::= { erpsPort1StatusEntry 4} 
 --xxx.100.39.4.3.1.5
erpsPort1BPR  OBJECT-TYPE
            SYNTAX      INTEGER    
            MAX-ACCESS  read-only
            STATUS      current
            DESCRIPTION
                "erps port1's BPR value."
            ::= { erpsPort1StatusEntry 5}
-----------------------------------------------
--xxx.100.39.5                      
erpsPortTrackConfig        	          OBJECT IDENTIFIER ::= { erpsMgt 5 }

--xxx.100.39.5.1            
erpsPortTrackConfigTable OBJECT-TYPE
    SYNTAX     SEQUENCE OF ErpsPortTrackConfigEntry
    MAX-ACCESS not-accessible
    STATUS     current
    DESCRIPTION
           "erps port0 failure-detect table."
    ::= { erpsPortTrackConfig 1 }
--xxx.100.39.5.2.1    
erpsPortTrackConfigEntry OBJECT-TYPE
    SYNTAX     ErpsPortTrackConfigEntry
    MAX-ACCESS not-accessible
    STATUS     current
    DESCRIPTION
            "A set of configuration parameters for erps port1 failure-detect."
    INDEX      {erpsRingNameIndex, erpsRingPortIndex}
    ::= { erpsPortTrackConfigTable 1 } 
    
ErpsPortTrackConfigEntry
        ::= SEQUENCE
            {                 
                erpsRingPortIndex                    INTEGER,
                erpsPortTrackProtocolType            INTEGER,          
                erpsPortTrackCfmDomain               DisplayString,
                erpsPortTrackCfmMaName	              DisplayString,
                erpsPortTrackCfmMaNum                INTEGER,
                erpsPortTrackCfmPvlanId              INTEGER,
                erpsPortTrackCfmMepId                INTEGER,
                erpsPortTrackCfmRmepId               INTEGER,
                erpsPortTrackRowStatus               INTEGER 
            } 
--xxx.100.39.5.2.1.1        
erpsRingPortIndex  OBJECT-TYPE
            SYNTAX      INTEGER
            {
               port0(0),
               port1(1)
            } 
            MAX-ACCESS  read-write
            STATUS      current
            DESCRIPTION
                "Domain."
            ::= { erpsPortTrackConfigEntry 1}
            
 --xxx.100.39.5.2.1.2
erpsPortTrackProtocolType  OBJECT-TYPE
            SYNTAX      INTEGER
            {
               cc(1),
               physical-link-or-cc(2)
            }    
            MAX-ACCESS  read-write
            STATUS      current
            DESCRIPTION
                "Failure type that ERPS ring's member port detect."
            ::= { erpsPortTrackConfigEntry 2}
--xxx.100.39.5.2.1.3        
erpsPortTrackCfmDomain   OBJECT-TYPE
            SYNTAX      DisplayString(SIZE (1..64)) 
            MAX-ACCESS  read-write
            STATUS      current
            DESCRIPTION
                "Domain."
            ::= { erpsPortTrackConfigEntry 3}
--xxx.100.39.5.2.1.4        
erpsPortTrackCfmMaName	   OBJECT-TYPE
            SYNTAX      DisplayString(SIZE (1..64)) 
            MAX-ACCESS  read-write
            STATUS      current
            DESCRIPTION
                "Service name string <1-45> character."
            ::= { erpsPortTrackConfigEntry 4}    
 --xxx.100.39.5.2.1.5
erpsPortTrackCfmMaNum  OBJECT-TYPE
            SYNTAX      INTEGER                
            MAX-ACCESS  read-write
            STATUS      current
            DESCRIPTION
                "Service name by numbe."
            ::= { erpsPortTrackConfigEntry 5}
 --xxx.100.39.5.2.1.6
erpsPortTrackCfmPvlanId  OBJECT-TYPE
            SYNTAX      INTEGER                
            MAX-ACCESS  read-write
            STATUS      current
            DESCRIPTION
                "Service name by primary vlan."
            ::= { erpsPortTrackConfigEntry 6} 
--xxx.100.39.5.2.1.7
erpsPortTrackCfmMepId  OBJECT-TYPE
            SYNTAX      INTEGER                
            MAX-ACCESS  read-write
            STATUS      current
            DESCRIPTION
                "Local mep configuartion."
            ::= { erpsPortTrackConfigEntry 7} 
--xxx.100.39.5.2.1.8
erpsPortTrackCfmRmepId  OBJECT-TYPE
            SYNTAX      INTEGER                
            MAX-ACCESS  read-write
            STATUS      current
            DESCRIPTION
                "Remote mep configuartion."
            ::= { erpsPortTrackConfigEntry 8} 
--xxx.100.39.5.2.1.9
erpsPortTrackRowStatus  OBJECT-TYPE
            SYNTAX      INTEGER 
            {
               unset(0),
               set(1)
            }               
            MAX-ACCESS  read-write
            STATUS      current
            DESCRIPTION
                "enable configuartion."
            ::= { erpsPortTrackConfigEntry 9} 
-----------------------------------------------
--xxx.100.39.6                      
erpsPortStatistics        	          OBJECT IDENTIFIER ::= { erpsMgt 6 }
--xxx.100.39.6.1
--erpsPort0TrackConfigTable           OBJECT IDENTIFIER ::= { erpsPortTrackConfig 1 } 
--xxx.100.39.6.2
--erpsPort1TrackConfigTable           OBJECT IDENTIFIER ::= { erpsPortTrackConfig 2 } 
--xxx.100.39.6.1            
erpsPort0StatisticsTable OBJECT-TYPE
    SYNTAX     SEQUENCE OF ErpsPort0StatisticsEntry
    MAX-ACCESS not-accessible
    STATUS     current
    DESCRIPTION
           "erps port0 Statistics table."
    ::= { erpsPortStatistics 1 }
--xxx.100.39.6.1.1   
erpsPort0StatisticsEntry OBJECT-TYPE
    SYNTAX     ErpsPort0StatisticsEntry
    MAX-ACCESS not-accessible
    STATUS     current
    DESCRIPTION
            "A set of results for erps port0 statistics."
    INDEX      {erpsRingNameIndex, erpsInstanceId}
    ::= { erpsPort0StatisticsTable 1 } 
    
ErpsPort0StatisticsEntry
        ::= SEQUENCE
            {
                erpsPort0TxRapsNrPktCnt               INTEGER,          
                erpsPort0RxRapsNrPktCnt               INTEGER,
                erpsPort0TxRapsNrRbPktCnt	          INTEGER,
                erpsPort0RxRapsNrRbPktCnt             INTEGER,
                erpsPort0TxRapsSfPktCnt               INTEGER,
                erpsPort0RxRapsSfPktCnt               INTEGER,
                erpsPort0TxRapsMsPktCnt               INTEGER,
                erpsPort0RxRapsMsPktCnt               INTEGER,
                erpsPort0TxRapsFsPktCnt               INTEGER,
                erpsPort0RxRapsFsPktCnt               INTEGER,
                erpsPort0TxRapsEventPktCnt            INTEGER,
                erpsPort0RxRapsEventPktCnt            INTEGER,
                erpsPort0TxRapsTotalPktCnt            INTEGER,
                erpsPort0RxRapsTotalPktCnt            INTEGER
            } 
            
 --xxx.100.39.6.1.1.1
erpsPort0TxRapsNrPktCnt  OBJECT-TYPE
            SYNTAX      INTEGER
            MAX-ACCESS  read-only
            STATUS      current
            DESCRIPTION
                "ERPS port0's Tx NR Packet Count."
            ::= { erpsPort0StatisticsEntry 1}
--xxx.100.39.6.1.1.2  
erpsPort0RxRapsNrPktCnt  OBJECT-TYPE
            SYNTAX      INTEGER
            MAX-ACCESS  read-only
            STATUS      current
            DESCRIPTION
                "ERPS port0's Rx NR Packet Count."
            ::= { erpsPort0StatisticsEntry 2}
--xxx.100.39.6.1.1.3  
erpsPort0TxRapsNrRbPktCnt  OBJECT-TYPE
            SYNTAX      INTEGER
            MAX-ACCESS  read-only
            STATUS      current
            DESCRIPTION
                "ERPS port0's Tx NR-RB Packet Count."
            ::= { erpsPort0StatisticsEntry 3}
--xxx.100.39.6.1.1.4  
erpsPort0RxRapsNrRbPktCnt  OBJECT-TYPE
            SYNTAX      INTEGER
            MAX-ACCESS  read-only
            STATUS      current
            DESCRIPTION
                "ERPS port0's Rx NR-RB Packet Count."
            ::= { erpsPort0StatisticsEntry 4}
--xxx.100.39.6.1.1.5  
erpsPort0TxRapsSfPktCnt  OBJECT-TYPE
            SYNTAX      INTEGER
            MAX-ACCESS  read-only
            STATUS      current
            DESCRIPTION
                "ERPS port0's Tx SF Packet Count."
            ::= { erpsPort0StatisticsEntry 5}
--xxx.100.39.6.1.1.6  
erpsPort0RxRapsSfPktCnt  OBJECT-TYPE
            SYNTAX      INTEGER
            MAX-ACCESS  read-only
            STATUS      current
            DESCRIPTION
                "ERPS port0's Rx SF Packet Count."
            ::= { erpsPort0StatisticsEntry 6} 
--xxx.100.39.6.1.1.7  
erpsPort0TxRapsMsPktCnt  OBJECT-TYPE
            SYNTAX      INTEGER
            MAX-ACCESS  read-only
            STATUS      current
            DESCRIPTION
                "ERPS port0's Tx MS Packet Count."
            ::= { erpsPort0StatisticsEntry 7}      
--xxx.100.39.6.1.1.8  
erpsPort0RxRapsMsPktCnt  OBJECT-TYPE
            SYNTAX      INTEGER
            MAX-ACCESS  read-only
            STATUS      current
            DESCRIPTION
                "ERPS port0's Rx MS Packet Count."
            ::= { erpsPort0StatisticsEntry 8}            
--xxx.100.39.6.1.1.9  
erpsPort0TxRapsFsPktCnt  OBJECT-TYPE
            SYNTAX      INTEGER
            MAX-ACCESS  read-only
            STATUS      current
            DESCRIPTION
                "ERPS port0's Tx FS Packet Count."
            ::= { erpsPort0StatisticsEntry 9}
--xxx.100.39.6.1.1.10  
erpsPort0RxRapsFsPktCnt  OBJECT-TYPE
            SYNTAX      INTEGER
            MAX-ACCESS  read-only
            STATUS      current
            DESCRIPTION
                "ERPS port0's Rx FS Packet Count."
            ::= { erpsPort0StatisticsEntry 10}
--xxx.100.39.6.1.1.11 
erpsPort0TxRapsEventPktCnt  OBJECT-TYPE
            SYNTAX      INTEGER
            MAX-ACCESS  read-only
            STATUS      current
            DESCRIPTION
                "ERPS port0's Tx Event Packet Count."
            ::= { erpsPort0StatisticsEntry 11}
--xxx.100.39.6.1.1.12 
erpsPort0RxRapsEventPktCnt  OBJECT-TYPE
            SYNTAX      INTEGER
            MAX-ACCESS  read-only
            STATUS      current
            DESCRIPTION
                "ERPS port0's Rx Event Packet Count."
            ::= { erpsPort0StatisticsEntry 12}
--xxx.100.39.6.1.1.13 
erpsPort0TxRapsTotalPktCnt   OBJECT-TYPE
            SYNTAX      INTEGER
            MAX-ACCESS  read-only
            STATUS      current
            DESCRIPTION
                "ERPS port0's Tx Total Packet Count."
            ::= { erpsPort0StatisticsEntry 13}               
--xxx.100.39.6.1.1.14 
erpsPort0RxRapsTotalPktCnt   OBJECT-TYPE
            SYNTAX      INTEGER
            MAX-ACCESS  read-only
            STATUS      current
            DESCRIPTION
                "ERPS port0's Rx Total Packet Count."
            ::= { erpsPort0StatisticsEntry 14}  
---xxx.100.39.6.2
erpsPort1StatisticsTable OBJECT-TYPE
    SYNTAX     SEQUENCE OF ErpsPort1StatisticsEntry
    MAX-ACCESS not-accessible
    STATUS     current
    DESCRIPTION
           "erps port1 Statistics table."
    ::= { erpsPortStatistics 2 }
--xxx.100.39.6.2.1    
erpsPort1StatisticsEntry OBJECT-TYPE
    SYNTAX     ErpsPort1StatisticsEntry
    MAX-ACCESS not-accessible
    STATUS     current
    DESCRIPTION
            "A set of results for erps port1 statistics."
    INDEX      {erpsRingNameIndex, erpsInstanceId}
    ::= { erpsPort1StatisticsTable 1 } 
    
ErpsPort1StatisticsEntry
        ::= SEQUENCE
            {
                erpsPort1TxRapsNrPktCnt               INTEGER,          
                erpsPort1RxRapsNrPktCnt               INTEGER,
                erpsPort1TxRapsNrRbPktCnt	          INTEGER,
                erpsPort1RxRapsNrRbPktCnt             INTEGER,
                erpsPort1TxRapsSfPktCnt               INTEGER,
                erpsPort1RxRapsSfPktCnt               INTEGER,
                erpsPort1TxRapsMsPktCnt               INTEGER,
                erpsPort1RxRapsMsPktCnt               INTEGER,
                erpsPort1TxRapsFsPktCnt               INTEGER,
                erpsPort1RxRapsFsPktCnt               INTEGER,
                erpsPort1TxRapsEventPktCnt            INTEGER,
                erpsPort1RxRapsEventPktCnt            INTEGER,
                erpsPort1TxRapsTotalPktCnt            INTEGER,
                erpsPort1RxRapsTotalPktCnt            INTEGER
            } 
            
 --xxx.100.39.6.2.1.1
erpsPort1TxRapsNrPktCnt  OBJECT-TYPE
            SYNTAX      INTEGER
            MAX-ACCESS  read-only
            STATUS      current
            DESCRIPTION
                "ERPS port1's Tx NR Packet Count."
            ::= { erpsPort1StatisticsEntry 1}
--xxx.100.39.6.2.1.2  
erpsPort1RxRapsNrPktCnt  OBJECT-TYPE
            SYNTAX      INTEGER
            MAX-ACCESS  read-only
            STATUS      current
            DESCRIPTION
                "ERPS port1's Rx NR Packet Count."
            ::= { erpsPort1StatisticsEntry 2}
--xxx.100.39.6.2.1.3  
erpsPort1TxRapsNrRbPktCnt  OBJECT-TYPE
            SYNTAX      INTEGER
            MAX-ACCESS  read-only
            STATUS      current
            DESCRIPTION
                "ERPS port1's Tx NR-RB Packet Count."
            ::= { erpsPort1StatisticsEntry 3}
--xxx.100.39.6.2.1.4  
erpsPort1RxRapsNrRbPktCnt  OBJECT-TYPE
            SYNTAX      INTEGER
            MAX-ACCESS  read-only
            STATUS      current
            DESCRIPTION
                "ERPS port1's Rx NR-RB Packet Count."
            ::= { erpsPort1StatisticsEntry 4}
--xxx.100.39.6.2.1.5  
erpsPort1TxRapsSfPktCnt  OBJECT-TYPE
            SYNTAX      INTEGER
            MAX-ACCESS  read-only
            STATUS      current
            DESCRIPTION
                "ERPS port1's Tx SF Packet Count."
            ::= { erpsPort1StatisticsEntry 5}
--xxx.100.39.6.2.1.6  
erpsPort1RxRapsSfPktCnt  OBJECT-TYPE
            SYNTAX      INTEGER
            MAX-ACCESS  read-only
            STATUS      current
            DESCRIPTION
                "ERPS port1's Rx SF Packet Count."
            ::= { erpsPort1StatisticsEntry 6} 
--xxx.100.39.6.2.1.7  
erpsPort1TxRapsMsPktCnt  OBJECT-TYPE
            SYNTAX      INTEGER
            MAX-ACCESS  read-only
            STATUS      current
            DESCRIPTION
                "ERPS port1's Tx MS Packet Count."
            ::= { erpsPort1StatisticsEntry 7}      
--xxx.100.39.6.2.1.8  
erpsPort1RxRapsMsPktCnt  OBJECT-TYPE
            SYNTAX      INTEGER
            MAX-ACCESS  read-only
            STATUS      current
            DESCRIPTION
                "ERPS port1's Rx MS Packet Count."
            ::= { erpsPort1StatisticsEntry 8}            
--xxx.100.39.6.2.1.9  
erpsPort1TxRapsFsPktCnt  OBJECT-TYPE
            SYNTAX      INTEGER
            MAX-ACCESS  read-only
            STATUS      current
            DESCRIPTION
                "ERPS port1's Tx FS Packet Count."
            ::= { erpsPort1StatisticsEntry 9}
--xxx.100.39.6.2.1.10  
erpsPort1RxRapsFsPktCnt  OBJECT-TYPE
            SYNTAX      INTEGER
            MAX-ACCESS  read-only
            STATUS      current
            DESCRIPTION
                "ERPS port1's Rx FS Packet Count."
            ::= { erpsPort1StatisticsEntry 10}
--xxx.100.39.6.2.1.11 
erpsPort1TxRapsEventPktCnt  OBJECT-TYPE
            SYNTAX      INTEGER
            MAX-ACCESS  read-only
            STATUS      current
            DESCRIPTION
                "ERPS port1's Tx Event Packet Count."
            ::= { erpsPort1StatisticsEntry 11}
--xxx.100.39.6.2.1.12 
erpsPort1RxRapsEventPktCnt  OBJECT-TYPE
            SYNTAX      INTEGER
            MAX-ACCESS  read-only
            STATUS      current
            DESCRIPTION
                "ERPS port1's Rx Event Packet Count."
            ::= { erpsPort1StatisticsEntry 12}
--xxx.100.39.6.2.1.13 
erpsPort1TxRapsTotalPktCnt   OBJECT-TYPE
            SYNTAX      INTEGER
            MAX-ACCESS  read-only
            STATUS      current
            DESCRIPTION
                "ERPS port1's Tx Total Packet Count."
            ::= { erpsPort1StatisticsEntry 13}               
--xxx.100.39.6.2.1.14 
erpsPort1RxRapsTotalPktCnt   OBJECT-TYPE
            SYNTAX      INTEGER
            MAX-ACCESS  read-only
            STATUS      current
            DESCRIPTION
                "ERPS port1's Rx Total Packet Count."
            ::= { erpsPort1StatisticsEntry 14}                                             
--********************************************************************************************************
-----------------------------------------------------------------------------------
--zhengmr 2017.9.19
--xxx.100.40 fdbMacInfo       
--***************************************
--fdbMacInfoTable
--***************************************
 
--xxx.100.40.1  fdbMacInfo
fdbMacInfoTable   OBJECT IDENTIFIER ::= { fdbMacInfo 1 }

--xxx.100.40.1.1
fdbMacMaxTotalNum  OBJECT-TYPE
            SYNTAX      INTEGER
            MAX-ACCESS  read-only
            STATUS      current
            DESCRIPTION
                "MAX total filter entry number."
            ::= { fdbMacInfoTable 1 }

--xxx.100.40.1.2
fdbMacMaxStaticNum   OBJECT-TYPE
            SYNTAX      INTEGER
            MAX-ACCESS  read-only
            STATUS      current
            DESCRIPTION
                "MAX static filter entry number."
            ::= { fdbMacInfoTable 2} 
--xxx.100.40.1.3
fdbMacMaxUnicastNum   OBJECT-TYPE
            SYNTAX      INTEGER
            MAX-ACCESS  read-only
            STATUS      current
            DESCRIPTION
                "MAX unicast filter entry number."
            ::= { fdbMacInfoTable 3} 
--xxx.100.40.1.4
fdbMacMaxMulticastNum   OBJECT-TYPE
            SYNTAX      INTEGER
            MAX-ACCESS  read-only
            STATUS      current
            DESCRIPTION
                "MAX multicast filter entry number."
            ::= { fdbMacInfoTable 4}             

--xxx.100.40.1.5
fdbMacCurTotalNum   OBJECT-TYPE
            SYNTAX      INTEGER
            MAX-ACCESS  read-only
            STATUS      current
            DESCRIPTION
                "CURRENT total filter entry number."
            ::= { fdbMacInfoTable 5} 
            
--xxx.100.40.1.6
fdbMacCurStaticNum OBJECT-TYPE
            SYNTAX      INTEGER    
            MAX-ACCESS  read-only
            STATUS      current
            DESCRIPTION
                "CURRENT static filter entry number."
            ::= { fdbMacInfoTable 6 }           

--xxx.100.40.1.7
fdbMacCurUnicastNum   OBJECT-TYPE
            SYNTAX      INTEGER
            MAX-ACCESS  read-only
            STATUS      current
            DESCRIPTION
                "CURRENT unicast filter entry number."
            ::= { fdbMacInfoTable 7} 
            
--xxx.100.40.1.8
fdbMacCurHiddenNum   OBJECT-TYPE
            SYNTAX      INTEGER
            MAX-ACCESS  read-only
            STATUS      current
            DESCRIPTION
                "CURRENT hidden filter entry number."
            ::= { fdbMacInfoTable 8}

--xxx.100.40.1.9
fdbMacCurMulticastInsertNum   OBJECT-TYPE
            SYNTAX      INTEGER
            MAX-ACCESS  read-only
            STATUS      current
            DESCRIPTION
                "CURRENT multicast insert filter entry number."
            ::= { fdbMacInfoTable 9}
			
--xxx.100.40.1.10
fdbMacCurMulticastWaitNum   OBJECT-TYPE
            SYNTAX      INTEGER
            MAX-ACCESS  read-only
            STATUS      current
            DESCRIPTION
                "CURRENT multicast wait filter entry number."
            ::= { fdbMacInfoTable 10}
			
--xxx.100.40.1.11
fdbMacCounterTimeStamp   OBJECT-TYPE
            SYNTAX      TimeStamp
            MAX-ACCESS  read-only
            STATUS      current
            DESCRIPTION
                "The value of sysUpTime when the fdbMacInfo was generated."
            ::= { fdbMacInfoTable 11}

--zhengmr end 

--********************************************************************************************************
--******************************************************************************************************** 
--xxx.100.200 Private LLDP Info

--xxx.100.200.1
lldpGlobalEnable OBJECT-TYPE
    SYNTAX  INTEGER{
                disable(0),
                enable(1)
            }
            MAX-ACCESS  read-write
            STATUS  current
            DESCRIPTION
                "Enable or disable lldp global config."
            ::= {lldpPrivateInfo 1 }    

--********************************************************************************************************       
                  
--**********************************************************************
--Mac Notification Global Group
--**********************************************************************            
macNotificationMibObjects OBJECT IDENTIFIER
    ::= { macNotificationMib 1 }                                                                            

-- MAC Notification MIB consists of the following groups
-- [1]  Mac Notification Global Group (cmnGlobalObjects).
-- [2]  Mac Notification Interface Group (cmnInterfaceObjects).
macNotificationGlobalObjects     OBJECT IDENTIFIER
    ::= { macNotificationMibObjects 1 }
macNotificationInterfaceObjects     OBJECT IDENTIFIER
    ::= { macNotificationMibObjects 2 }

macNotificationGlobalFeatureEnabled  OBJECT-TYPE
    SYNTAX        TruthValue
    MAX-ACCESS    read-write
    STATUS        current
    DESCRIPTION
        "Indicates whether the MAC notification feature is currently 
        running in the device.

        Setting this object to false(2) disables the MAC notification
        feature globally thus disabling the feature at each interface.

        Setting this object to true(1) will start the MAC notification
        feature running in the device. If the feature is already
        running, setting to true(1) has no effect. Once the MAC
        notification is enabled, whether the feature is running at each
        interface is controlled by the macNotificationIfConfigTable."   
    ::= { macNotificationGlobalObjects 1 }

macNotificationNotificationInterval  OBJECT-TYPE
    SYNTAX        Counter32
    UNITS         "seconds"
    MAX-ACCESS    read-only
    STATUS        current
    DESCRIPTION
        "This object specifies the maximum interval of time between
        macNotificationMacChangedNotifications being generated by the device.
        If the value of macNotificationNotificationsEnabled is true(1), the
        device will send out the generated macNotificationMacChangedNotifications
        and archive the MAC change notification events in the
        macNotificationHistoryTable. If the value of macNotificationNotificationEnabled is
        false(2), the device will not send out the generated
        macNotificationMacChangedNotifications but it will archive these events
        in the macNotificationHistoryTable.   
        
        If the value of this object is equal to 0, the device will 
        generate macNotificationMacChangedNotifications and archive the MAC 
        change notification events in the macNotificationHistoryTable as soon as
        there is MAC address learnt or removed by the device.

        If the value of this object is greater than 0, the device will
        wait for a period of time equal to the value of this object
        before generate the macNotificationMacChangedNotifications and archive
        the MAC change notification events in the macNotificationHistoryTable."
    ::= { macNotificationGlobalObjects 2 }

macNotificationMacAddressesLearnt OBJECT-TYPE
    SYNTAX        Counter32 
    MAX-ACCESS    read-only
    STATUS        current
    DESCRIPTION
        "Indicates the number of MAC addresses learnt by the
        device." 
    ::= { macNotificationGlobalObjects 3 }

macNotificationMacAddressesRemoved OBJECT-TYPE
    SYNTAX        Counter32 
    MAX-ACCESS    read-only
    STATUS        current
    DESCRIPTION
        "Indicates the number of MAC addresses removed from the
        forwarding database." 
    ::= { macNotificationGlobalObjects 4 }

macNotificationNotificationsEnabled OBJECT-TYPE
     SYNTAX          TruthValue
     MAX-ACCESS      read-write
     STATUS          current
     DESCRIPTION
         "Indicates whether macNotificationMacChangedNotification notifications
          will or will not be sent when there are MAC addresses
          learnt or removed from the device's forwarding database. 
          Disabling notifications does not prevent the MAC address
          info from being added to the macNotificationHistoryTable."
     DEFVAL { false }
     ::= { macNotificationGlobalObjects 5 }

macNotificationNotificationsSent OBJECT-TYPE
    SYNTAX         Counter32 
    MAX-ACCESS     read-only
    STATUS         current
    DESCRIPTION
        "Indicates the number of macNotificationMacChangedNotifications sent out
        by the device."
    ::= { macNotificationGlobalObjects 6 }

macNotificationHistTableMaxLength OBJECT-TYPE
    SYNTAX          Counter32
    UNITS           "entries"
    MAX-ACCESS      read-only
    STATUS          current
    DESCRIPTION
        "The upper limit on the number of entries that the
        macNotificationHistoryTable may contain.  A value of 0 will
        prevent any history from being retained. When this
        table is full, the oldest entry will be deleted and
        a new one will be created."
    ::= { macNotificationGlobalObjects 7 }

macNotificationHistoryTable OBJECT-TYPE
    SYNTAX     SEQUENCE OF MacNotificationHistoryEntry
    MAX-ACCESS not-accessible
    STATUS     current
    DESCRIPTION
        "This table will archive the MAC change notification events 
        generated by this device. The MAC change notification
        events are archived here even if macNotificationMacChangesNotifications 
        are not actually sent."
    ::= { macNotificationGlobalObjects 8 }

macNotificationHistoryEntry OBJECT-TYPE
    SYNTAX     MacNotificationHistoryEntry
    MAX-ACCESS not-accessible
    STATUS     current
    DESCRIPTION
        "A MAC change notification message that was previously
        generated by this device.  Each entry is indexed by a message
        index."
    INDEX   { macNotificationHistIndex }
    ::= { macNotificationHistoryTable 1 }

MacNotificationHistoryEntry ::=
    SEQUENCE {
        macNotificationHistIndex
                Counter32,
        macNotificationHistMacChangedMsg
                OCTET STRING,
        macNotificationHistTimestamp
                TimeStamp
    }

macNotificationHistIndex OBJECT-TYPE
    SYNTAX          Counter32
    MAX-ACCESS      read-only
    STATUS          current
    DESCRIPTION
        "An index that uniquely identifies a MAC change notification
        event previously generated by the device. This index starts at
        1 and increases by one when a MAC change notification is 
        generated.  When it reaches the maximum value, the agent wraps
        the value back to 1."
    ::= { macNotificationHistoryEntry 1 }

macNotificationHistMacChangedMsg OBJECT-TYPE
    SYNTAX        OCTET STRING (SIZE(1..254))
    MAX-ACCESS    read-only
    STATUS        current
    DESCRIPTION
        "This object contains the information of a MAC change
        notification event. It consists of several tuples packed
        together in the format of '<tuple1><tuple2>...'.
        
        Each tuple consist of 11 octets in the format of
        '<operation><VLAN><MAC><dot1dBasePort>' where 

        <operation> is of size 1 octet and supports the following values
          0 - End of MIB object.
          1 - MAC learnt.
          2 - MAC removed.

        <VLAN> is VLAN number of the VLAN which the MAC address is
        belonged to and has size of 2 octet.

        <MAC> is the Layer2 Mac Address and has size of 6 octets.

        <dot1dBasePort> is the value of dot1dBasePort for the
        interface from which the MAC address is learnt and has size
        of 2 octets."
    ::= { macNotificationHistoryEntry 2 }

macNotificationHistTimestamp  OBJECT-TYPE
    SYNTAX          TimeStamp
    MAX-ACCESS      read-only
    STATUS          current
    DESCRIPTION
        "The value of sysUpTime when the macNotificationMacChangedNotification
        containing the information denoted by the macNotificationHistMacChangedMsg
        object in this entry was generated."
    ::= { macNotificationHistoryEntry 3 }

--*********************************************************************
--  Mac Notification Interface Group
--*********************************************************************

--
-- macNotificationIfConfigTable
--
macNotificationIfConfigTable  OBJECT-TYPE
    SYNTAX        SEQUENCE OF MacNotificationIfConfigEntry
    MAX-ACCESS    not-accessible
    STATUS        current
    DESCRIPTION
        "This table enables or disables the generation of notification
        at each interface when MAC address is learnt or removed." 
    ::= { macNotificationInterfaceObjects 1 }

macNotificationIfConfigEntry  OBJECT-TYPE
    SYNTAX        MacNotificationIfConfigEntry
    MAX-ACCESS    not-accessible
    STATUS        current
    DESCRIPTION
        "Each entry contains the configuration for enabling the
        MAC notification at each interface that supports this
        feature." 
	INDEX { ifIndex }
    ::= { macNotificationIfConfigTable 1 }

MacNotificationIfConfigEntry  ::= SEQUENCE {
    macNotificationMacAddrLearntEnable    TruthValue, 
    macNotificationMacAddrRemovedEnable   TruthValue 
}

macNotificationMacAddrLearntEnable OBJECT-TYPE
    SYNTAX        TruthValue 
    MAX-ACCESS    read-write
    STATUS        current
    DESCRIPTION
        "Indicates whether this interface is enabled to send 
        macNotificationMacChangedNotification when it learns a new MAC address. This
        variable has no effect when the value of macNotificationGlobalFeatureEnabled
        object is false(2).

        Setting this object to true(1) enables the sending of
        macNotificationMacChangedNotification when this interface learns a 
        new MAC address.

        Setting this object to false(2) disables the sending
        of macNotificationMacChangedNotification when this interface learns
        a new MAC address."      
    DEFVAL { false }
    ::= { macNotificationIfConfigEntry 1 }

macNotificationMacAddrRemovedEnable OBJECT-TYPE
    SYNTAX        TruthValue 
    MAX-ACCESS    read-write
    STATUS        current
    DESCRIPTION
        "Indicates whether this interface is enabled to send 
        macNotificationMacChangedNotification when a MAC address which it learnt
        previously is removed from the forwarding table. This variable
        has no effect when the value of macNotificationGlobalFeatureEnabled object
        is false(2). 

        Setting this object to true(1) enables the sending of
        macNotificationMacChangedNotification when a MAC address which this
        interface learnt previously is removed from the forwarding
        table.

        Setting this object to false(2) disables the sending of
        macNotificationMacChangedNotification when a MAC address which this
        interface learnt previously is removed from the forwarding
        table."
    DEFVAL { false }
    ::= { macNotificationIfConfigEntry 2 }

--******************************************************************************************************** 
                                                         
--trap  
--xxx.101.100 
    antiArpscan                    OBJECT IDENTIFIER ::= { notifications 100 }  
--********************************************************************************************************      
       
--xxx.101.100.1   
    prohibitPortOID NOTIFICATION-TYPE
                            STATUS current
                            DESCRIPTION "anti arp scan prohibit port."
                            ::= { antiArpscan 1 }
--xxx.101.100.2   
    recoverPortOID NOTIFICATION-TYPE
                            STATUS current
                            DESCRIPTION "anti arp scan recover port."
                            ::= { antiArpscan 2 }
--xxx.101.100.3      
    prohibitIPOID NOTIFICATION-TYPE
                            STATUS current
                            DESCRIPTION "anti arp scan  prohibit ip."
                            ::= { antiArpscan 3 }
--xxx.101.100.4   
    prohibitIPExceedSlimitOID NOTIFICATION-TYPE
                            STATUS current
                            DESCRIPTION "anti arp scan  prohibit ip exceed S limit."
                            ::= { antiArpscan 4 }
--xxx.101.100.5   
    prohibitIPExceedHlimitOID NOTIFICATION-TYPE
                            STATUS current
                            DESCRIPTION "anti arp scan prohibit ip exceed H limit."
                            ::= { antiArpscan 5 }
--xxx.101.100.6   
    recoverIPOID NOTIFICATION-TYPE
                            STATUS current
                            DESCRIPTION "anti arp scan recover ip."
                            ::= { antiArpscan 6 }
--xxx.101.100.7   
    ipAddress NOTIFICATION-TYPE
                            STATUS current
                            DESCRIPTION "anti arp scan ip address."
                            ::= { antiArpscan 7 }        
--xxx.101.100.8   
    arpSpeedLimitOID NOTIFICATION-TYPE
                            STATUS current
                            DESCRIPTION "anti arp scan speed limit."
                            ::= { antiArpscan 8 }
--xxx.101.100.9   
    arpDiscardOID NOTIFICATION-TYPE
                            STATUS current
                            DESCRIPTION "anti arp scan discard arp."
                            ::= { antiArpscan 9 }
--xxx.101.100.10   
    recoverArpSpeedOID NOTIFICATION-TYPE
                            STATUS current
                            DESCRIPTION "anti arp scan recover arp speed."
                            ::= { antiArpscan 10 }
--xxx.101.100.11   
    recoverArpDiscardOID NOTIFICATION-TYPE
                            STATUS current
                            DESCRIPTION "anti arp scan recover arp discard."
                            ::= { antiArpscan 11 }        
                          
--********************************************************************************************************  
--********************************************************************************************************  
--trap  
--xxx.101.101 
    fan                    OBJECT IDENTIFIER ::= { notifications 101 }  
--******************************************************************************************************** 
--xxx.101.101.1
fanAbnormalOID NOTIFICATION-TYPE
                            STATUS current
                            DESCRIPTION "fan abnormal."
                            ::= { fan 1 }
--xxx.101.101.2  
fanNormalOID NOTIFICATION-TYPE
                            STATUS current
                            DESCRIPTION "fan normal."
                            ::= { fan 2 } 
--xxx.101.101.3
fanInsertOID NOTIFICATION-TYPE
                            STATUS current
                            DESCRIPTION "fan insert."
                            ::= { fan 3 }
--xxx.101.101.4
fanPullOutOID NOTIFICATION-TYPE
                            STATUS current
                            DESCRIPTION "fan pull out."
                            ::= { fan 4 }

--********************************************************************************************************  
--trap  
--xxx.101.102
    power                    OBJECT IDENTIFIER ::= { notifications 102 }      
--******************************************************************************************************** 
--xxx.101.102.1
powerAbnormalOID NOTIFICATION-TYPE
                            STATUS current
                            DESCRIPTION "sys power DC is working!"
                            ::= { power 1 }
--xxx.101.102.2    
powerNormalOID NOTIFICATION-TYPE
                            STATUS current
                            DESCRIPTION "sys power AC is working!"
                            ::= { power 2 }
--xxx.101.102.3
powerInsertOID NOTIFICATION-TYPE
                            STATUS current
                            DESCRIPTION "sys power insert!"
                            ::= { power 3 }
--xxx.101.102.4			
powerPullOutOID NOTIFICATION-TYPE
                            STATUS current
                            DESCRIPTION "sys power pull out!"
                            ::= { power 4 }

--********************************************************************************************************  
--trap  
--xxx.101.103 
    slotTemperature                    OBJECT IDENTIFIER ::= { notifications 103 }   
--******************************************************************************************************** 
--xxx.101.103.1
slotTemperatureHigherOID NOTIFICATION-TYPE
                            STATUS current
                            DESCRIPTION "Temperature breached high threshold"
                            ::= { slotTemperature 1 }
--xxx.101.103.2 
slotTemperatureLowerOID NOTIFICATION-TYPE
                            STATUS current
                            DESCRIPTION "Temperature breached low threshold"
                            ::= { slotTemperature 2 } 

--********************************************************************************************************  
--trap  
--xxx.101.103 
--    slotTemperature  OBJECT 	IDENTIFIER ::= { notifications 103 }
    
--******************************************************************************************************** 

--********************************************************************************************************  
--trap  
--xxx.101.104 
    dhcpsnooping                    OBJECT IDENTIFIER ::= { notifications 104 }     
--******************************************************************************************************** 
--xxx.101.104.1   
    shutdownPort NOTIFICATION-TYPE
                            STATUS current
                            DESCRIPTION "dhcp snooping shutdown port."
                            ::= { dhcpsnooping 1 }
--xxx.101.104.2   
    noShutdownPort NOTIFICATION-TYPE
                            STATUS current
                            DESCRIPTION "dhcp snooping no shutdown port."
                            ::= { dhcpsnooping 2 }
--xxx.101.104.3      
    addBlackhole NOTIFICATION-TYPE
                            STATUS current
                            DESCRIPTION "dhcp snooping add black hole."
                            ::= { dhcpsnooping 3 }
--xxx.101.104.4   
    delBlackhole NOTIFICATION-TYPE
                            STATUS current
                            DESCRIPTION "dhcp snooping delete black hole."
                            ::= { dhcpsnooping 4 }
--xxx.101.104.5   
    addBlockedinfo NOTIFICATION-TYPE
                            STATUS current
                            DESCRIPTION "dhcp snooping add blocked information."
                            ::= { dhcpsnooping 5 }
--********************************************************************************************************     

--trap  
--xxx.101.105 
    rateViolation                    OBJECT IDENTIFIER ::= { notifications 105 }   
--******************************************************************************************************** 
--xxx.101.105.1
rateViolationShutdownPort NOTIFICATION-TYPE
                            STATUS current
                            DESCRIPTION "rate violation shutdown port."
                            ::= { rateViolation 1 }
--xxx.101.105.2  
rateViolationNoShutdownPort NOTIFICATION-TYPE
                            STATUS current
                            DESCRIPTION "rate violation no shutdown port."
                            ::= { rateViolation 2 } 
--******************************************************************************************************** 

--trap  
--xxx.101.106 
    portGroup                    OBJECT IDENTIFIER ::= { notifications 106 }    
--******************************************************************************************************** 
--xxx.101.106.1
    portGroupCreate NOTIFICATION-TYPE
                            STATUS current
                            DESCRIPTION "port group create."
                            ::= { portGroup 1 }
--xxx.101.106.2  
    portGroupDelete NOTIFICATION-TYPE
                            STATUS current
                            DESCRIPTION "port group delete."
                            ::= { portGroup 2 } 
--xxx.101.106.3  
    portGroupUpdate NOTIFICATION-TYPE
                            STATUS current
                            DESCRIPTION "port group update."
                            ::= { portGroup 3 } 
--******************************************************************************************************** 
--trap  
--xxx.101.110 
    transceiverMonitor  OBJECT 	IDENTIFIER ::= { notifications 110 }    
--******************************************************************************************************** 
--xxx.101.110.1
    transceiverMonitorAlarmEvent NOTIFICATION-TYPE
                            STATUS current
                            DESCRIPTION "tranceiver monitor alarm event."
                            ::= { transceiverMonitor 1 }
--xxx.101.110.2  
    transceiverMonitorWarnEvent NOTIFICATION-TYPE
                            STATUS current
                            DESCRIPTION "transceiver monitor warn event."
                            ::= { transceiverMonitor 2 } 
--********************************************************************************************************    
--trap  
--xxx.101.109
    efmOam                    OBJECT IDENTIFIER ::= { notifications 109 }     
--******************************************************************************************************** 
--xxx.101.109.1 
    efmOamDiscoverySuccess NOTIFICATION-TYPE
                            STATUS current
                            DESCRIPTION "efm oam discovery success."
                            ::= { efmOam 1 }
--xxx.101.109.2
    efmOamDiscoveryTimeout NOTIFICATION-TYPE
                            STATUS current
                            DESCRIPTION "efm oam discovery time out."
                            ::= { efmOam 2 }
--xxx.101.109.3
    efmOamLocalErrSymbolPeriodEvent NOTIFICATION-TYPE
                            STATUS current
                            DESCRIPTION "efm oam local error symbol period event."
                            ::= { efmOam 3 }
--xxx.101.109.4 
    efmOamLocalErrFramePeriodEvent NOTIFICATION-TYPE
                            STATUS current
                            DESCRIPTION "efm oam local error frame period event."
                            ::= { efmOam 4 } 
--xxx.101.109.5  
    efmOamLocalErrFrameEvent NOTIFICATION-TYPE
                            STATUS current
                            DESCRIPTION "efm oam local error frame event."
                            ::= { efmOam 5 } 
--xxx.101.109.6  
    efmOamLocalErrFrameSecondsSummaryEvent NOTIFICATION-TYPE
                            STATUS current
                            DESCRIPTION "efm oam local error frame seconds summary event."
                            ::= { efmOam 6 }
--xxx.101.109.7
    efmOamLocalLinkFault NOTIFICATION-TYPE
                            STATUS current
                            DESCRIPTION "efm oam local link fault."
                            ::= { efmOam 7 } 
--xxx.101.109.8  
    efmOamLocalCriticalEvent NOTIFICATION-TYPE
                            STATUS current
                            DESCRIPTION "efm oam local critical event."
                            ::= { efmOam 8 } 
--xxx.101.109.9  
    efmOamRemoteErrSymbolPeriodEvent NOTIFICATION-TYPE
                            STATUS current
                            DESCRIPTION "efm oam remote error symbol period event."
                            ::= { efmOam 9 } 
--xxx.101.109.10 
    efmOamRemoteErrFramePeriodEvent NOTIFICATION-TYPE
                            STATUS current
                            DESCRIPTION "efm oam remote error frame period event."
                            ::= { efmOam 10 }  
--xxx.101.109.11 
    efmOamRemoteErrFrameEvent NOTIFICATION-TYPE
                            STATUS current
                            DESCRIPTION "efm oam remote error frame event."
                            ::= { efmOam 11 } 
--xxx.101.109.12  
    efmOamRemoteErrFrameSecondsSummaryEvent NOTIFICATION-TYPE
                            STATUS current
                            DESCRIPTION "efm oam remote error frame seconds summary event."
                            ::= { efmOam 12 } 
--xxx.101.109.13 
    efmOamRemoteLinkFault NOTIFICATION-TYPE
                            STATUS current
                            DESCRIPTION "efm oam remote link fault."
                            ::= { efmOam 13 }
--xxx.101.109.14  
    efmOamRemoteCriticalEvent NOTIFICATION-TYPE
                            STATUS current
                            DESCRIPTION "efm oam remote critical event."
                            ::= { efmOam 14 }  
--xxx.101.109.15  
    efmOamRemoteDyingGasp NOTIFICATION-TYPE
                            STATUS current
                            DESCRIPTION "efm oam remote dying gasp."
                            ::= { efmOam 15 }
--xxx.101.109.16  
    efmOamLoopBackSuccess NOTIFICATION-TYPE
                            STATUS current
                            DESCRIPTION "efm oam loopback success."
                            ::= { efmOam 16 } 
--xxx.101.109.17  
    efmOamLoopBackExit NOTIFICATION-TYPE
                            STATUS current
                            DESCRIPTION "efm oam loopback exit."
                            ::= { efmOam 17 } 
--********************************************************************************************************       
--trap  
--xxx.101.114 
    dyingGasp  OBJECT 	IDENTIFIER ::= { notifications 114 }    
--******************************************************************************************************** 
--xxx.101.110.1
    dyingGaspEvent NOTIFICATION-TYPE
                            STATUS current
                            DESCRIPTION "dying gasp."
                            ::= { dyingGasp 1 }    
--xxx.101.116
    copyRunningConfig  OBJECT 	IDENTIFIER ::= { notifications 116 }    
--******************************************************************************************************** 
--xxx.101.110.1
    copyRunningConfigEvent NOTIFICATION-TYPE
                            STATUS current
                            DESCRIPTION "copy running config event."
                            ::= { copyRunningConfig 1 }  
 
--********************************************************************************************************  
--trap  
--xxx.101.121
    mstp                    OBJECT IDENTIFIER ::= { notifications 121 }      
--******************************************************************************************************** 
--xxx.101.121.1
mstpTcnTrapOID NOTIFICATION-TYPE
                            STATUS current
                            DESCRIPTION "mstp tcn."
                            ::= { mstp 1 } 
--trap  
--xxx.101.122
    powerGroup                    OBJECT IDENTIFIER ::= { notifications 122 }    
--******************************************************************************************************** 
--xxx.101.106.1
   -- powerSupplyChassisTrap NOTIFICATION-TYPE
   --                       STATUS current
   --                       DESCRIPTION "power supply chassis."
   --                       ::= { powerGroup  1 }
--xxx.101.106.2  
    powerSupplyTrap NOTIFICATION-TYPE
                            STATUS current
                            DESCRIPTION "power supply."
                            ::= { powerGroup  2 } 
--xxx.101.106.3  
   -- powerPresentChassisTrap NOTIFICATION-TYPE
   --                       STATUS current
   --                       DESCRIPTION "power present chassis."
   --                       ::= { powerGroup  3 } 
--xxx.101.106.4  
    powerPresentTrap NOTIFICATION-TYPE
                            STATUS current
                            DESCRIPTION "power present."
                            ::= { powerGroup  4 }         
--********************************************************************************************************  
--trap  
--xxx.101.125
    erpsGroup                    OBJECT IDENTIFIER ::= { notifications 125 }      
--******************************************************************************************************** 
--xxx.101.125.1
   swERPSSFDetectedTrap NOTIFICATION-TYPE
                            STATUS current
                            DESCRIPTION "ERPS SF deleted."
                            ::= { erpsGroup  1 }
--xxx.101.125.2
   swERPSSFClearedTrap NOTIFICATION-TYPE
                            STATUS current
                            DESCRIPTION "ERPS SF cleared."
                            ::= { erpsGroup  2 }
--******************************************************************************************************** 
--trap  
--xxx.101.126
    authLogGroup  OBJECT 	IDENTIFIER ::= { notifications 126 }    
--******************************************************************************************************** 
--xxx.101.126.1
    authLogin NOTIFICATION-TYPE
                            STATUS current
                            DESCRIPTION "User Login."
                            ::= { authLogGroup 1 }    
--xxx.101.126.2
    authLogout NOTIFICATION-TYPE
                            STATUS current
                            DESCRIPTION "User Logout."
                            ::= { authLogGroup 2 }


--******************************************************************************************************** 
--vpls peer state change trap  wangyangah 2019-06-04
--xxx.101.127
    vpls                    OBJECT IDENTIFIER ::= { notifications 127 }
--xxx.101.127.1
vplsPeerStateChangeTrapOID NOTIFICATION-TYPE
                            STATUS current
                            DESCRIPTION "Vpls peer state change."
                            ::= { vpls 1 }
--******************************************************************************************************** 
--vpws peer state change trap 
--xxx.101.128
    vpws                    OBJECT IDENTIFIER ::= { notifications 128 }
--xxx.101.128.1
vpwsPeerStateChangeTrapOID NOTIFICATION-TYPE
                            STATUS current
                            DESCRIPTION "Vpws peer state change."
                            ::= { vpws 1 }
--********************************************************************************************************
--route alarm information
--xxx.101.130
    routeAlarm            OBJECT IDENTIFIER ::= { notifications 130 }
--xxx.101.130.1
routeAlarmTrapOID      NOTIFICATION-TYPE
                            STATUS current
                            DESCRIPTION "route alarm information"
                            ::= { routeAlarm 1 }
--********************************************************************************************************

 END
